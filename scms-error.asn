-- 
--  Copyright 2017, 2018 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-------------------------------------------------------------------------------
-- SCMS-ERRORS
--
-- The structure in this file defines the possible error occuring during the 
-- management of component certificates.
--
-- This file is part of the SCMS protocol developed by CAMP VSC5
-- It depends on the IEEE 1609.2 protocol specification
-------------------------------------------------------------------------------

-- @namespace Ieee1609dot2ScmsError 
Ieee1609dot2ScmsError {iso(1) identified-organization(3) ieee(111)
standards-association-numbered-series-standards(2) wave-stds(1609)  dot2(2)
scms(4) errors(2) complete (1) major-version-2(2)}


DEFINITIONS AUTOMATIC TAGS ::= BEGIN 

EXPORTS ALL;

IMPORTS 

  ScmsCommonError
FROM Ieee1609dot2ScmsCommonError {iso(1) identified-organization(3) ieee(111)
standards-association-numbered-series-standards(2) wave-stds(1609) dot2(2)
scms(4) errors(2) common(2) major-version-2(2)}

  ComponentCertificateManagementError
FROM Ieee1609Dot2ScmsComponentCertificateManagementError
    {iso(1) identified-organization(3) ieee(111) 
    standards-association-numbered-series-standards(2) wave-stds(1609)  
    dot2(2) scms(4) errors(2) component-certificate-management(3) major-version-2(2)}

  EcaEndEntityError
FROM Ieee1609Dot2EcaEndEntityError
    {iso(1) identified-organization(3) ieee(111) 
    standards-association-numbered-series-standards(2) wave-stds(1609)  
    dot2(2) scms(4) errors(2) eca-ee(5) major-version-2(2)}

  LaMaError
FROM Ieee1609Dot2LaMaError
    {iso(1) identified-organization(3) ieee(111) 
    standards-association-numbered-series-standards(2) wave-stds(1609)  
    dot2(2) scms(4) errors(2) la-ma(9) major-version-2(2)}

  LaPcaError
FROM Ieee1609Dot2LaPcaError
    {iso(1) identified-organization(3) ieee(111) 
    standards-association-numbered-series-standards(2) wave-stds(1609)  
    dot2(2) scms(4) errors(2) la-pca(10) major-version-2(2)}

  LaRaError
FROM Ieee1609Dot2LaRaError
    {iso(1) identified-organization(3) ieee(111) 
    standards-association-numbered-series-standards(2) wave-stds(1609)  
    dot2(2) scms(4) errors(2) la-ra(11) major-version-2(2)}

  MaPcaError
FROM Ieee1609Dot2MaPcaError
    {iso(1) identified-organization(3) ieee(111) 
    standards-association-numbered-series-standards(2) wave-stds(1609)  
    dot2(2) scms(4) errors(2) ma-pca(13) major-version-2(2)}

  MaRaError
FROM Ieee1609Dot2MaRaError
    {iso(1) identified-organization(3) ieee(111) 
    standards-association-numbered-series-standards(2) wave-stds(1609)  
    dot2(2) scms(4) errors(2) ma-ra(14) major-version-2(2)}

  PcaRaError
FROM Ieee1609Dot2PcaRaError
    {iso(1) identified-organization(3) ieee(111) 
    standards-association-numbered-series-standards(2) wave-stds(1609)  
    dot2(2) scms(4) errors(2) pca-ra(15) major-version-2(2)}
	
  RaPgError
FROM Ieee1609Dot2RaPgError
{iso(1) identified-organization(3) ieee(111) 
standards-association-numbered-series-standards(2) wave-stds(1609)  
dot2(2) scms(4) errors(2) ra-pg(16) major-version-2(2)}

;

---
-- @brief Possible errors in the SCMS
-- @class ScmsError 
-- @param
-- @see 
ScmsError ::= CHOICE {
  common  ScmsCommonError,
  ccm     ComponentCertificateManagementError,
  eca-ee  EcaEndEntityError,
  la-ma   LaMaError,
  la-pca  LaPcaError,
  la-ra   LaRaError,
  ma-pca  MaPcaError,
  ma-ra   MaRaError,
  pca-ra  PcaRaError,
  ra-pg   RaPgError,
  ...
}


---
-- @brief Management of certificates of SCMS component errors
-- @class ScopedComponentCertificateManagementError 
-- @param
-- @see 
ScopedComponentCertificateManagementError ::= 
  ScmsError (WITH COMPONENTS {common} | WITH COMPONENTS {ccm})

---
-- @brief ECA-EE errors
-- @class ScopedEcaEndEntityError 
-- @param
-- @see 
ScopedEcaEndEntityError ::= 
  ScmsError (WITH COMPONENTS {common} | WITH COMPONENTS {eca-ee})

---
-- @brief This type is not used (see following la-ma errors)
-- @class ScopedLaMaError 
-- @param
-- @see 
ScopedLaMaError ::=
  ScmsError (WITH COMPONENTS {common} | WITH COMPONENTS {la-ma})

---
-- @brief Linkage information request errors
-- @class ScopedLaMaLIError 
-- @param
-- @see 
ScopedLaMaLIError ::=
  ScmsError (WITH COMPONENTS {common} | 
             WITH COMPONENTS {la-ma 
                (WITH COMPONENTS {la-ma-base-error} |
                 WITH COMPONENTS {la-ma-linkage-info-error})}
            )
---
-- @brief Linkage seed request errors
-- @class ScopedLaMaLSError 
-- @param
-- @see 
ScopedLaMaLSError ::=
  ScmsError (WITH COMPONENTS {common} | 
             WITH COMPONENTS {la-ma 
                (WITH COMPONENTS {la-ma-base-error} |
                 WITH COMPONENTS {la-ma-linkage-seed-error})}
            )

---
-- @brief LA-PCA errors
-- @class ScopedLaPcaError 
-- @param
-- @see 
ScopedLaPcaError ::= 
  ScmsError (WITH COMPONENTS {common} | WITH COMPONENTS {la-pca})

---
-- @brief LA-RA errors
-- @class ScopedLaRaError 
-- @param
-- @see 
ScopedLaRaError ::= 
  ScmsError (WITH COMPONENTS {common} | WITH COMPONENTS {la-ra})

---
-- @brief MA-PCA errors
-- @class ScopedMaPcaError 
-- @param
-- @see 
ScopedMaPcaError ::= 
  ScmsError (WITH COMPONENTS {common} | WITH COMPONENTS {ma-pca})

---
-- @brief MA-RA errors 
-- @class ScopedMaRaError 
-- @param
-- @see 
ScopedMaRaError ::= 
  ScmsError (WITH COMPONENTS {common} | WITH COMPONENTS {ma-ra})
---
-- @brief Blacklist request errors
-- @class ScopedMaRaBlacklistError 
-- @param
-- @see 
ScopedMaRaBlacklistError ::=
  ScmsError (WITH COMPONENTS {common} | 
             WITH COMPONENTS {ma-ra
                (WITH COMPONENTS {ma-ra-base-error} |
                 WITH COMPONENTS {ma-ra-blacklist-error})}
            )
---
-- @brief Linkage chain identifier request errors
-- @class ScopedMaRaLCIError 
-- @param
-- @see 
ScopedMaRaLCIError ::=
  ScmsError (WITH COMPONENTS {common} | 
             WITH COMPONENTS {ma-ra
                (WITH COMPONENTS {ma-ra-base-error} |
                 WITH COMPONENTS {ma-ra-lci-error})}
            )



---
-- @brief PCA-RA errors
-- @class ScopedPcaRaError 
-- @param
-- @see 
ScopedPcaRaError ::= 
  ScmsError (WITH COMPONENTS {common} | WITH COMPONENTS {pca-ra})
  
---
-- @brief 
-- @class ScopedPcaRaError 
-- @param
-- @see 
ScopedRaPgError ::= 
  ScmsError (WITH COMPONENTS {common} | WITH COMPONENTS {ra-pg})


END
