-- 
--  Copyright 2017, 2018 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-------------------------------------------------------------------------------
-- MA-PCA-ERRORS
--
-- The structures in this file define the possible error occuring during a 
-- message exchange between the MA and the PCA.
--
-- This file is part of the SCMS protocol developed by CAMP VSC5
-- It depends on the IEEE 1609.2 protocol specification
-------------------------------------------------------------------------------

-- @namespace Ieee1609Dot2MaPcaError
Ieee1609Dot2MaPcaError
{iso(1) identified-organization(3) ieee(111) 
standards-association-numbered-series-standards(2) wave-stds(1609)  
dot2(2) scms(4) errors(2) ma-pca (13) major-version-2(2)}

DEFINITIONS AUTOMATIC TAGS ::= BEGIN

EXPORTS ALL;

---
-- @brief Generic structure containing the possible errors returned by the PCA.
-- @class MaPcaError 
-- @param
-- @see 
MaPcaError ::= CHOICE {
	ma-pca	MaPcaErrorCode,
  ...
}

---
-- @brief 
-- @class MaPcaErrorCode 
-- @param
-- @see 
MaPcaErrorCode ::= ENUMERATED {
    pcaInternalTimeout,
    maRequestTimeout,
    pcaNoMaAuthorizationSignature,
    pcaInvalidMaAuthorizationSignature,
    numberofRequestsExceeded, -- not used yet
    pcaNumberOfLinkageValuesExceeded,
    noSecureConnectiontoRequestor, -- not used yet
    tooManyUsers, -- not used yet
    linkageValueUnknown, -- not used yet
    pcaInvalidLinkageValue,
    pcaInvalidInputValueFormat,
  ...
}



END
