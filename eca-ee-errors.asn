-- 
--  Copyright 2017, 2018 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-------------------------------------------------------------------------------
-- ECA-EE-ERRORS
--
-- The structure in this file defines the possible error returned by the ECA 
-- following a request by an OBE to obtain a new enrollment certificate.
--
-- This file is part of the SCMS protocol developed by CAMP VSC5
-- It depends on the IEEE 1609.2 protocol specification
-------------------------------------------------------------------------------

-- @namespace Ieee1609Dot2EcaEndEntityError
Ieee1609Dot2EcaEndEntityError
{iso(1) identified-organization(3) ieee(111) 
standards-association-numbered-series-standards(2) wave-stds(1609)  
dot2(2) scms(4) errors(2) eca-ee (5) major-version-2(2)}

DEFINITIONS AUTOMATIC TAGS ::= BEGIN

EXPORTS ALL;

---
-- @brief 
-- @class EcaEndEntityError 
-- @param
-- @see 
EcaEndEntityError ::= ENUMERATED {
  ecaInvalidCurrentTime,        -- currentTime out of range
  ecaInvalidRequestedStartTime, -- requestedStartTime out of range
  ecaInvalidPsid,               -- passed PSID is invalid for the enrollment
  ecaInvalidValidityPeriod,     -- ValidityPeriod out of range
  ecaInvalidRegion,             -- GeographicRegion out of range
  ecaInvalidAssuranceLevel,     -- SubjectAssurance out of range
  ecaInvalidEncryptionKey,      -- response encryption key (PublicEncryptionKey) is invalid
  ecaInvalidVerifyKey,          -- enrollment key (SignedPublicKey) is invalid
  ecaMalformedRequest,          -- everything else that can go wrong in the request 
  ecaInternalServerError,       -- ECA failed to process Enrollment
  ecaResponseTimeout,           -- ECA response timeout
  ...
}



END
