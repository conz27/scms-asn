-- 
--  Copyright 2017, 2018 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-------------------------------------------------------------------------------
-- MA-RA-ERRORS
--
-- The structures in this file define the possible error occuring during a 
-- message exchange between the MA and the RA.
--
-- This file is part of the SCMS protocol developed by CAMP VSC5
-- It depends on the IEEE 1609.2 protocol specification
-------------------------------------------------------------------------------

-- @namespace Ieee1609Dot2MaRaError
Ieee1609Dot2MaRaError
{iso(1) identified-organization(3) ieee(111) 
standards-association-numbered-series-standards(2) wave-stds(1609)  
dot2(2) scms(4) errors(2) ma-ra(14) major-version-2(2)}

DEFINITIONS AUTOMATIC TAGS ::= BEGIN

EXPORTS ALL;


---
-- @brief Generic structure containing the possible errors returned by the RA.
-- @class MaRaError 
-- @param
-- @see 
MaRaError ::= CHOICE {
  ma-ra-base-error          MaRaBaseErrorCode,
  ma-ra-blacklist-error     MaRaBlacklistErrorCode,
  ma-ra-lci-error           MaRaLCIErrorCode,
  ma-ra-cdv-error           MaRaCDVErrorCode,    -- Added for RSE revocation
  ...
}

---
-- @brief 
-- @class MaRaBaseErrorCode 
-- @param
-- @see 
MaRaBaseErrorCode ::= ENUMERATED {
	raInternalTimeout,
        maRequestTimeout,
        raNoMaAuthorizationSignature, 
	raInvalidMaAuthorizationSignature,
        raInvalidInputValueFormat,
        raInvalidHashRequest,
        raInvalidRIFValue,
        raInvalidLinkageValue, 
	raNumberOfRequestsExceeded,
	noSecureConnectionToRequestor, -- not used yet
	hpcrIsUnknownToRA, -- not used yet
	...
}

---
-- @brief 
-- @class MaRaBlacklistErrorCode 
-- @param
-- @see 
MaRaBlacklistErrorCode ::= ENUMERATED {
	-- HPCR points to already blacklisted certificate
	alreadyBlacklisted,
	-- raCertificateAlreadyBlacklisted,
	...
}

---
-- @brief 
-- @class MaRaLCIErrorCode 
-- @param
-- @see 
MaRaLCIErrorCode ::= ENUMERATED {
	noLinkageChainIdentifiersKnownForHPCR, -- not used yet
	...
}

-- Added for RSE application and OBE identification cert revocation
---
-- @brief 
-- @class MaRaCDVErrorCode 
-- @param
-- @see 
MaRaCDVErrorCode ::= ENUMERATED {
    noCertificateDigestValuesKnownForRIF,
    ...
}
    
END
