-- 
--  Copyright 2017, 2018 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-------------------------------------------------------------------------------
-- LA-RA-ERRORS
--
-- The structure in this file defines the possible error occuring during a 
-- message exchange between an LA and the RA.
--
-- This file is part of the SCMS protocol developed by CAMP VSC5
-- It depends on the IEEE 1609.2 protocol specification
-------------------------------------------------------------------------------

-- @namespace Ieee1609Dot2LaRaError
Ieee1609Dot2LaRaError
{iso(1) identified-organization(3) ieee(111) 
standards-association-numbered-series-standards(2) wave-stds(1609)  
dot2(2) scms(4) errors(2) la-ra(11) major-version-2(2)}

DEFINITIONS AUTOMATIC TAGS ::= BEGIN

EXPORTS ALL;

---
-- @brief Generic structure containing the possible errors returned by the LA.
-- @class LaRaError 
-- @param
-- @see 
LaRaError ::= CHOICE {
	la-ra	LaRaErrorCode,
	...
}

---
-- @brief 
-- @class LaRaErrorCode 
-- @param
-- @see 
LaRaErrorCode ::= ENUMERATED {
  invalidPcaKey,        -- no valid key for encryption to PCA available
  invalidIMin,          -- iMin is invalid
  invalidIMax,          -- iMax is invalid
  invalidContinueChain, -- continue chain is neither 0 nor 1
  invalidLinkagechainId,-- linkagechainId is invalid
  invalidJMax,          -- invalid jMax value (e.g. too large)
  ...
}


END
