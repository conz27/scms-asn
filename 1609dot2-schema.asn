IEEE1609dot2 {iso(1) identified-organization(3) ieee(111) 
standards-association-numbered-series-standards(2) wave-stds(1609)  
dot2(2) base (1) schema (1)}

--******************************************************************************
-- 
-- IEEE P1609.2 Data Types 
-- 
--******************************************************************************

 DEFINITIONS AUTOMATIC TAGS ::= BEGIN 
 
EXPORTS ALL;

IMPORTS 
  CrlSeries,
  EccNistP256CurvePoint,
  EciesNistP256EncryptedKey,
  EncryptionKey,
  GeographicRegion,
  GroupLinkageValue,
  HashAlgorithm,
  HashedId3,
  HashedId32,
  HashedId8,
  Hostname,
  IValue,
  LinkageValue,
  Opaque,
  PKAlgorithm,
  Psid,
  PsidSsp,
  PsidSspRange,
  PublicEncryptionKey,
  PublicVerificationKey,
  SequenceOfPsidSsp,
  SequenceOfPsidSspRange,
  Signature,
  Ssp,
  SubjectAssurance,
  SymmetricEncryptionKey,
  ThreeDLocation,
  Time64,
  Time64WithStandardDeviation,
  Uint16, 
  Uint3,
  Uint32,
  Uint8,
  ValidityPeriod
FROM IEEE1609dot2BaseTypes {iso(1) identified-organization(3) ieee(111) 
    standards-association-numbered-series-standards(2) wave-stds(1609)  
    dot2(2) base(1) base-types(2)}

;

  TestPsidGroupPermissions ::= PsidGroupPermissions


-- 
--********************************************************************* 
-- 
--  Structures for describing secured data
-- 
--*********************************************************************  

  SignedDataPayload ::= SEQUENCE  { 
      data             Ieee1609Dot2Data OPTIONAL,
      extDataHash      OCTET STRING (SIZE (32)) OPTIONAL,
      ...
  }
      (WITH COMPONENTS {..., data PRESENT} |
       WITH COMPONENTS {..., extDataHash PRESENT})
       -- must include at least one element


  Ieee1609Dot2Data ::= SEQUENCE  { 
    protocolVersion    Uint8(3),
    content            Ieee1609Dot2Content
  }

  Ieee1609Dot2Content ::=  CHOICE  { 
    unsecuredData             Opaque, 
    signedData                SignedData,
    encryptedData             EncryptedData,
    signedCertificateRequest  SignedCertificateRequest,
    ...
  }

  SignedData ::= SEQUENCE  { 
    hashId          HashAlgorithm,
    tbsData         ToBeSignedData,
    signer          SignerIdentifier,
    signature       Signature
  }

  SignerIdentifier ::= CHOICE    { 
    digest          HashedId8,
    certificate     SequenceOfCertificate,
    self            NULL,
    ...
  }

  ToBeSignedData ::= SEQUENCE  { 
    payload         SignedDataPayload,
    headerInfo      HeaderInfo
  }


  HeaderInfo ::= SEQUENCE  { 
      psid                   Psid,
      generationTime         Time64WithStandardDeviation OPTIONAL,
      expiryTime             Time64  OPTIONAL,
      generationLocation     ThreeDLocation OPTIONAL,
      missingCertIdentifier  HashedId3 OPTIONAL,
      missingCrlIdentifier   MissingCrlIdentifier OPTIONAL,
      encryptionKey          EncryptionKey OPTIONAL,
      ...
  }


  -- NEW, designed to support epidemic distribution in 1609.2 setting.
  MissingCrlIdentifier ::=                  
        SEQUENCE  { caId            HashedId8,
                    crlSeries       Uint32,
                    crlSerial       Uint32,
                    chunkId         Uint16
                  }

  -- New, designed to support aggregated signatures
  Countersignature ::= Ieee1609Dot2Data (WITH COMPONENTS {...,
    content (WITH COMPONENTS {..., 
      signedData  (WITH COMPONENTS {..., 
        tbsData (WITH COMPONENTS {..., 
          payload (WITH COMPONENTS {..., 
            data ABSENT,
            extDataHash PRESENT
          }),
          headerInfo (WITH COMPONENTS {..., 
            generationTime PRESENT,
            expiryTime ABSENT,
            generationLocation ABSENT,
            missingCertIdentifier ABSENT,
            missingCrlIdentifier ABSENT,
            encryptionKey ABSENT
          })
        })
      })
    })
  })

--********************************************************************** 
-- 
--  Structures for describing encrypted data
-- 
--**********************************************************************  


  EncryptedData ::=
        SEQUENCE  { recipients     SequenceOfRecipientInfo,
                    ciphertext     SymmetricCiphertext
                  }

  -- The three different PKRecipientInfo types are to let the receiver know how
  -- to look up the decryption key:
  -- * certRecipInfo: The data was encrypted using the encryption key in a cert.
  --   This field contains the HashedId8 of the cert.
  -- * signedDataRecipInfo: The data was encrypted using the response encryption
  --   key from a SignedData. This field contains the HashedId8 of the
  --   Ieee1609Dot2Data containing the SignedData containing the encryption key.
  -- * rekRecipInfo: The data was encrypted using a response encryption key. The
  --   structure contains the HashedId8 of the response encryption key. This
  --   should only be used if the SignedData is not available as it potentially
  --   allows misbinding attacks: it is included in these structures
  --   specifically to enable certificate response encryption from the PCA
  --   to the end-entity device.
  RecipientInfo ::=
        CHOICE    { symmRecipInfo       SymmRecipientInfo,
                    certRecipInfo       PKRecipientInfo, 
                    signedDataRecipInfo PKRecipientInfo, 
                    rekRecipInfo        PKRecipientInfo 
                  }
         
  SequenceOfRecipientInfo ::= SEQUENCE OF RecipientInfo

  SymmRecipientInfo ::= HashedId8

  PKRecipientInfo ::= SEQUENCE  { 
    recipientId        HashedId8, 
    encKey             EncryptedDataEncryptionKey
  }

  EncryptedDataEncryptionKey ::= CHOICE  { 
       eciesNistp256   EciesNistP256EncryptedKey,
       ...
  }

  SymmetricCiphertext ::=
        CHOICE  { aes128ccm           AesCcmCiphertext,
                  ...
                 }

  AesCcmCiphertext ::=
        SEQUENCE  { nonce           OCTET STRING (SIZE (12)),
                    ccmCiphertext   Opaque -- 16 bytes longer than plaintext
                  }



--********************************************************************** 
-- 
--  Certificate Request
-- 
--**********************************************************************  

  SignedCertificateRequest ::= SEQUENCE  { 
    hashId          HashAlgorithm,
    tbsRequest      ToBeSignedCertificateRequest,
    signer          SignerIdentifier,
    signature       Signature
  }

  ToBeSignedCertificateRequest ::= SEQUENCE {
    data            OCTET STRING,
    encryptionKey   EncryptionKey
  }



--********************************************************************** 
-- 
--  Certificates and other security management data structures
--  Based more on 103 097 than 1609.2 but with WSA certs and implicit certs
--  supported
-- 
--********************************************************************** 

-- Certificates are implicit (type = implicit, toBeSigned includes 
-- reconstruction value, signature absent) or explicit (type = explicit,
-- toBeSigned includes verification key, signature present).

  Certificate ::= CertificateBase (ImplicitCertificate | ExplicitCertificate)

  SequenceOfCertificate ::= SEQUENCE OF Certificate

  CertificateBase ::=
        SEQUENCE  { version                 Uint8(1),
                    type                    CertificateType,
                    issuer                  IssuerIdentifier,
                    toBeSigned              ToBeSignedCertificate,
                    signature               Signature OPTIONAL
                  }
  
  CertificateType  ::= ENUMERATED {
      explicit,
      implicit,
      ...
  }

  ImplicitCertificate ::= CertificateBase (WITH COMPONENTS {...,
      type(implicit),
      toBeSigned(WITH COMPONENTS {..., 
          verifyKeyIndicator(WITH COMPONENTS {reconstructionValue})
      }), 
      signature ABSENT
  })

  ExplicitCertificate ::= CertificateBase (WITH COMPONENTS {...,
      type(explicit),
      toBeSigned(WITH COMPONENTS {..., 
          verifyKeyIndicator(WITH COMPONENTS {verificationKey})
      }), 
      signature PRESENT
  })

  IssuerIdentifier ::= CHOICE  { 
    ecdsaNistP256AndDigest  HashedId8,
    self                    HashAlgorithm,
    ...
  }

  ToBeSignedCertificate ::= SEQUENCE  { 
    id                     CertificateId,
    crlSeries              CrlSeries,
    validityPeriod         ValidityPeriod,
    region                 GeographicRegion OPTIONAL,
    assuranceLevel         SubjectAssurance OPTIONAL,
    appPermissions         SequenceOfPsidSsp OPTIONAL,
    certIssuePermissions   SequenceOfPsidGroupPermissions OPTIONAL,
    explicitCertReqPermissions 
                           SequenceOfPsidGroupPermissions OPTIONAL, 
    canRequestRollover     NULL OPTIONAL,
    encryptionKey          PublicEncryptionKey OPTIONAL,
    verifyKeyIndicator     VerificationKeyIndicator,
    ...
  }
  (WITH COMPONENTS { ..., appPermissions PRESENT} |
   WITH COMPONENTS { ..., certIssuePermissions PRESENT} |
   WITH COMPONENTS { ..., explicitCertReqPermissions PRESENT})

   CertificateId ::= CHOICE {
        linkageData             LinkageData,
        name                    Hostname,
        binaryId                OCTET STRING(SIZE(1..64)),
        ...
    }

  LinkageData ::= 
        SEQUENCE  { iValue                IValue,
                    linkage-value         LinkageValue, 
                    group-linkage-value   GroupLinkageValue OPTIONAL
                  }
         
  CertIssuancePermissions ::= BIT STRING {app (0), enrol (1) }

  PsidGroupPermissions ::= SEQUENCE {
      subjectPsids       SubjectPsids,
      minChainDepth      INTEGER DEFAULT 1, -- 0 for enrolment certs
      chainDepthRange    INTEGER DEFAULT 0, -- max depth = min + range
      certType           CertIssuancePermissions DEFAULT {app}
  }

  SequenceOfPsidGroupPermissions ::= SEQUENCE OF PsidGroupPermissions

  SubjectPsids ::= CHOICE {
          explicit        SequenceOfPsidSspRange,
          all             NULL,
          ...
  }


  VerificationKeyIndicator ::= CHOICE {
        verificationKey         PublicVerificationKey,
        reconstructionValue     EccNistP256CurvePoint
  }


  
--********************************************************************** 
-- Data Types required for internal processing of transmitted and received
-- data but which are not needed for transmitted messages.
--
--********************************************************************** 

  PublicKeyReconstructionHashInput ::= -- Note, reverse order from 1609.2-2013
        SEQUENCE  { subjectCertificate      Certificate,
                    issuerHash              HashedId32
                  }


END
