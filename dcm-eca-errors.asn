Ieee1609Dot2DcmEcaError
{iso(1) identified-organization(3) ieee(111) 
standards-association-numbered-series-standards(2) wave-stds(1609)  
dot2(2) scms(2) errors(2) dcm-eca (4)}

DEFINITIONS AUTOMATIC TAGS ::= BEGIN

EXPORTS ALL;

DcmEcaError ::= ENUMERATED {
  ...
}



END
