-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 
-- 
-- Output of registry data into file:
-- C:\Program Files (x86)\MiniEdit/Source.ASN
-- in format need to operate on the ASN source files.
-- 
-- Run on Mini-Edit Version 3.2.454 from dgpstools.com
-- From file: ...\revisedASN\J2735_r63.its
-- Last Changed:  [Mod: 9/1/2015 7:28:45 PM]
-- This export was created on 9/1/2015  at 7:29:03 PM 
-- ###################################################
-- 
-- 
-- Run this file with a line like:
-- asn1 source.txt -errorfile errs.txt -noun
-- 
-- The local module consisting of DEs / DFs and MSGs
REGION DEFINITIONS AUTOMATIC TAGS::= BEGIN 
 
-- -_-_-_-_-_-_-_-_-_-_-_-_-_-_-_-_-_-_-_-_-_-_-_-_-_-_-_-_
-- 
-- Start of entries from table Dialogs...
-- This table typicaly contains dialog and operational exchange entries.
-- -_-_-_-_-_-_-_-_-_-_-_-_-_-_-_-_-_-_-_-_-_-_-_-_-_-_-_-_
-- 
 
 
-- DF_REG_DataFrames (Desc Name) Record 1
Reg-DataFrames ::=  SEQUENCE { ... } -- placeholder
--
-- Regional data frames with no current extension markers
--
Reg-AdvisorySpeed         DSRC.REG-EXT-ID-AND-TYPE ::= { ...  }
Reg-ComputedLane          DSRC.REG-EXT-ID-AND-TYPE ::= { ...  }
Reg-EventDescription      DSRC.REG-EXT-ID-AND-TYPE ::= { ...  }
Reg-GenericLane           DSRC.REG-EXT-ID-AND-TYPE ::= { ...  }
Reg-GeographicalPath      DSRC.REG-EXT-ID-AND-TYPE ::= { ...  }
Reg-GeometricProjection   DSRC.REG-EXT-ID-AND-TYPE ::= { ...  }
Reg-IntersectionGeometry  DSRC.REG-EXT-ID-AND-TYPE ::= { ...  }
Reg-LaneAttributes        DSRC.REG-EXT-ID-AND-TYPE ::= { ...  }
Reg-MovementState         DSRC.REG-EXT-ID-AND-TYPE ::= { ...  }
Reg-NodeAttributeSetLL    DSRC.REG-EXT-ID-AND-TYPE ::= { ...  }
Reg-NodeAttributeSetXY    DSRC.REG-EXT-ID-AND-TYPE ::= { ...  }
Reg-NodeOffsetPointLL     DSRC.REG-EXT-ID-AND-TYPE ::= { ...  }
Reg-RequestorDescription  DSRC.REG-EXT-ID-AND-TYPE ::= { ...  }
Reg-RequestorType         DSRC.REG-EXT-ID-AND-TYPE ::= { ...  }
Reg-RoadSegment           DSRC.REG-EXT-ID-AND-TYPE ::= { ...  }
Reg-SignalControlZone     DSRC.REG-EXT-ID-AND-TYPE ::= { ...  }
Reg-SignalRequest         DSRC.REG-EXT-ID-AND-TYPE ::= { ...  }
Reg-SignalRequestPackage  DSRC.REG-EXT-ID-AND-TYPE ::= { ...  }
Reg-SignalStatus          DSRC.REG-EXT-ID-AND-TYPE ::= { ...  }
Reg-SignalStatusPackage   DSRC.REG-EXT-ID-AND-TYPE ::= { ...  }
Reg-SupplementalVehicleExtensions DSRC.REG-EXT-ID-AND-TYPE ::= { ...  }
Reg-VehicleClassification DSRC.REG-EXT-ID-AND-TYPE ::= { ...  }
Reg-VerticalOffset        DSRC.REG-EXT-ID-AND-TYPE ::= { ...  }

--
-- Data Frames with current adopted expansion point content
--
Reg-ConnectionManeuverAssist DSRC.REG-EXT-ID-AND-TYPE ::= { 
   { AddGrpC.ConnectionManeuverAssist-addGrpC IDENTIFIED BY DSRC.addGrpC} ,
   ... 
   }

Reg-IntersectionState     DSRC.REG-EXT-ID-AND-TYPE ::= { 
   { AddGrpC.IntersectionState-addGrpC IDENTIFIED BY DSRC.addGrpC} ,
   ... 
   }

Reg-LaneDataAttribute     DSRC.REG-EXT-ID-AND-TYPE ::= { 
   { AddGrpB.LaneDataAttribute-addGrpB IDENTIFIED BY DSRC.addGrpB} ,
   ... 
   }  

Reg-MovementEvent         DSRC.REG-EXT-ID-AND-TYPE ::= { 
   { AddGrpB.MovementEvent-addGrpB IDENTIFIED BY DSRC.addGrpB} ,
   ... 
   }   

Reg-NodeOffsetPointXY     DSRC.REG-EXT-ID-AND-TYPE ::= { 
   { AddGrpB.NodeOffsetPointXY-addGrpB IDENTIFIED BY DSRC.addGrpB} ,
   ... 
   }   

Reg-Position3D            DSRC.REG-EXT-ID-AND-TYPE ::= { 
   { AddGrpB.Position3D-addGrpB IDENTIFIED BY DSRC.addGrpB} |
   { AddGrpC.Position3D-addGrpC IDENTIFIED BY DSRC.addGrpC} ,
   ... 
   }   

Reg-RestrictionUserType   DSRC.REG-EXT-ID-AND-TYPE ::= { 
   { AddGrpC.RestrictionUserType-addGrpC IDENTIFIED BY DSRC.addGrpC} ,
   ... 
   }   



-- 
-- The pattern used for regional adaptions is shown below
-- Use:
-- the text 'XXX' below is used to represent the name of the entry
-- the region should replace 'xxx-RegionName' with its own Type Def
-- a name patern such as 'DataFrameName-RegionName' is recommended
-- the 'regionName' value must be assigned from the RegionId element
-- this value would defined in the REGION module, unless a well-known 
-- region was being used (these IDs are defined in the DSRC module)
-- refer to the full standard for additional details
--
--Reg-XXX DSRC.REG-EXT-ID-AND-TYPE ::= {
--   { XXX-RegionName IDENTIFIED BY regionName  },
--   ... 
--}
--regionName DSRC.RegionId ::= 128 
--XXX-RegionName ::= SEQUENCE { ... }
--
-- End example pattern for regional use
 
 
 
-- DF_REG_MessageExpansionFramework (Desc Name) Record 2
Reg-MessageExpansionFramework ::=  SEQUENCE { ... } -- placeholder
-- Extension markers for operational messages in the standard
-- Messages with no adopted extension markers in the standard
Reg-BasicSafetyMessage     DSRC.REG-EXT-ID-AND-TYPE ::= { ... }
Reg-CommonSafetyRequest    DSRC.REG-EXT-ID-AND-TYPE ::= { ... }
Reg-EmergencyVehicleAlert  DSRC.REG-EXT-ID-AND-TYPE ::= { ... }
Reg-IntersectionCollision  DSRC.REG-EXT-ID-AND-TYPE ::= { ... }
Reg-NMEAcorrections        DSRC.REG-EXT-ID-AND-TYPE ::= { ... }
Reg-ProbeDataManagement    DSRC.REG-EXT-ID-AND-TYPE ::= { ... }
Reg-ProbeVehicleData       DSRC.REG-EXT-ID-AND-TYPE ::= { ... }
Reg-RoadSideAlert          DSRC.REG-EXT-ID-AND-TYPE ::= { ... }
Reg-RTCMcorrections        DSRC.REG-EXT-ID-AND-TYPE ::= { ... }
Reg-SignalRequestMessage   DSRC.REG-EXT-ID-AND-TYPE ::= { ... }
Reg-SignalStatusMessage    DSRC.REG-EXT-ID-AND-TYPE ::= { ... }
Reg-SPAT                   DSRC.REG-EXT-ID-AND-TYPE ::= { ... }
Reg-TravelerInformation    DSRC.REG-EXT-ID-AND-TYPE ::= { ... }
Reg-PersonalSafetyMessage  DSRC.REG-EXT-ID-AND-TYPE ::= { ... }

-- Messages with current adopted extension marker content
Reg-MapData                DSRC.REG-EXT-ID-AND-TYPE ::= { 
   { AddGrpC.MapData-addGrpC IDENTIFIED BY DSRC.addGrpC},
   ... 
   }
 
 
 
-- DF_REG_TestMessageExpansionFramework (Desc Name) Record 3
Reg-TestMessageExpansionFramework ::=  SEQUENCE { ... }
-- Test Messages
Reg-TestMessage00    DSRC.REG-EXT-ID-AND-TYPE ::= { ... }
Reg-TestMessage01    DSRC.REG-EXT-ID-AND-TYPE ::= { ... }
Reg-TestMessage02    DSRC.REG-EXT-ID-AND-TYPE ::= { ... }
Reg-TestMessage03    DSRC.REG-EXT-ID-AND-TYPE ::= { ... }
Reg-TestMessage04    DSRC.REG-EXT-ID-AND-TYPE ::= { ... }
Reg-TestMessage05    DSRC.REG-EXT-ID-AND-TYPE ::= { ... }
Reg-TestMessage06    DSRC.REG-EXT-ID-AND-TYPE ::= { ... }
Reg-TestMessage07    DSRC.REG-EXT-ID-AND-TYPE ::= { ... }
Reg-TestMessage08    DSRC.REG-EXT-ID-AND-TYPE ::= { ... }
Reg-TestMessage09    DSRC.REG-EXT-ID-AND-TYPE ::= { ... }
Reg-TestMessage10    DSRC.REG-EXT-ID-AND-TYPE ::= { ... }
Reg-TestMessage11    DSRC.REG-EXT-ID-AND-TYPE ::= { ... }
Reg-TestMessage12    DSRC.REG-EXT-ID-AND-TYPE ::= { ... }
Reg-TestMessage13    DSRC.REG-EXT-ID-AND-TYPE ::= { ... }
Reg-TestMessage14    DSRC.REG-EXT-ID-AND-TYPE ::= { ... }
Reg-TestMessage15    DSRC.REG-EXT-ID-AND-TYPE ::= { ... }
 

END
-- The local module consisting of DEs / DFs and MSGs
DSRC DEFINITIONS AUTOMATIC TAGS::= BEGIN 

-- -_-_-_-_-_-_-_-_-_-_-_-_-_-_-_-_-_-_-_-_-_-_-_-_-_-_-_-_
-- 
-- Start of entries from table Messages...
-- This table typicaly contains message entries.
-- -_-_-_-_-_-_-_-_-_-_-_-_-_-_-_-_-_-_-_-_-_-_-_-_-_-_-_-_
-- 
 
 
-- MSG_BasicSafetyMessage (BSM) (Desc Name) Record 1
BasicSafetyMessage ::=  SEQUENCE {
   -- Part I, Sent at all times with each message
   coreData      BSMcoreData,   

   -- Part II Content
   safetyExt     VehicleSafetyExtensions       OPTIONAL,
   special       SpecialVehicleExtensions      OPTIONAL,
   supplemental  SupplementalVehicleExtensions OPTIONAL,

   regional      RegionalExtension {{REGION.Reg-BasicSafetyMessage}} OPTIONAL,
   ...
   }
 
 
 
-- MSG_CommonSafetyRequest (CSR) (Desc Name) Record 2
CommonSafetyRequest ::=  SEQUENCE {
   timeStamp   MinuteOfTheYear             OPTIONAL,
   msgCnt      MsgCount                    OPTIONAL, 
   id          TemporaryID                 OPTIONAL,               
   requests    RequestedItemList,
   -- Note: Above no longer uses the same request as probe management
   regional    RegionalExtension {{REGION.Reg-CommonSafetyRequest}} OPTIONAL,
   ...
   }
 
 
 
-- MSG_EmergencyVehicleAlert (EVA) (Desc Name) Record 3
EmergencyVehicleAlert ::=  SEQUENCE {
   timeStamp       MinuteOfTheYear OPTIONAL,
   id              TemporaryID OPTIONAL, 
   rsaMsg          RoadSideAlert, 
		   -- the DSRCmsgID inside this 
                   -- data frame is set as per the 
                   -- RoadSideAlert.  The CRC is
                   -- set to a value of zero. <-## Conflicts with remarks
   responseType    ResponseType                   OPTIONAL, 
   details         EmergencyDetails               OPTIONAL,   
                   -- Combines these 3 items: 
                   -- SirenInUse,                     
                   -- LightbarInUse,                  
                   -- MultiVehicleReponse,

   mass            VehicleMass                    OPTIONAL,
   basicType       VehicleType                    OPTIONAL,  
                                -- gross size and axle cnt
   
   -- type of vehicle and agency when known
   vehicleType     ITIS.VehicleGroupAffected      OPTIONAL,      
   responseEquip   ITIS.IncidentResponseEquipment OPTIONAL, 
   responderType   ITIS.ResponderGroupAffected    OPTIONAL,    
   regional        RegionalExtension {{REGION.Reg-EmergencyVehicleAlert}} OPTIONAL,
   ...
   }
 
 
 
-- MSG_IntersectionCollisionAvoidance  (ICA) (Desc Name) Record 4
IntersectionCollision ::=  SEQUENCE {
   msgCnt         MsgCount,                 
   id             TemporaryID,               
   timeStamp      MinuteOfTheYear OPTIONAL,
   partOne        BSMcoreData OPTIONAL, 
   path           PathHistory OPTIONAL, 
                  -- a set of recent path histories
   pathPrediction PathPrediction OPTIONAL,
                  -- the predicted path
   intersetionID  IntersectionReferenceID, 
                  -- the applicable Intersection
   laneNumber     ApproachOrLane,
                  -- the best applicable Lane or Approach
   eventFlag      VehicleEventFlags,
                  -- used to convey vehicle Panic Events,  
                  -- Set to indicate "Intersection Violation" 
   regional      RegionalExtension {{REGION.Reg-IntersectionCollision}} OPTIONAL,
   ...
   }
 
 
 
-- MSG_MapData  (MAP) (Desc Name) Record 5
MapData ::=  SEQUENCE {
   timeStamp         MinuteOfTheYear OPTIONAL, 
   msgIssueRevision  MsgCount,        
   layerType         LayerType OPTIONAL,
   layerID           LayerID  OPTIONAL,
   intersections     IntersectionGeometryList OPTIONAL,
                     -- All Intersection definitions 
   
   -- NOTE:
   -- Other map data will be added here as it is defined
   -- (curve warnings, construction routes, etc.)
   -- as an example of this:
   roadSegments      RoadSegmentList OPTIONAL,
                     -- All roadway descriptions
  
   dataParameters    DataParameters OPTIONAL,
                     -- Any meta data regarding the map contents
   
   restrictionList   RestrictionClassList OPTIONAL,
                     -- Any restriction ID tables which have  
                     -- established for these map entries 
   regional          RegionalExtension {{REGION.Reg-MapData}} OPTIONAL,
   ...
   }
 
 
 
-- MSG_MessageFrame (FRAME) (Desc Name) Record 6
MessageFrame ::=  SEQUENCE {
   messageId   MESSAGE-ID-AND-TYPE.&id({MessageTypes}),
   value       MESSAGE-ID-AND-TYPE.&Type({MessageTypes}{@.messageId}),
   ...
   }

MESSAGE-ID-AND-TYPE ::= CLASS {
   &id    DSRCmsgID UNIQUE,
   &Type
   } WITH SYNTAX {&Type IDENTIFIED BY &id}

MessageTypes MESSAGE-ID-AND-TYPE ::= {
   { BasicSafetyMessage    IDENTIFIED BY basicSafetyMessage    } |       
   { MapData               IDENTIFIED BY mapData               } |          
   { SPAT                  IDENTIFIED BY signalPhaseAndTimingMessage } | 
   { CommonSafetyRequest   IDENTIFIED BY commonSafetyRequest   } |  
   { IntersectionCollision IDENTIFIED BY intersectionCollision } |  
   { NMEAcorrections       IDENTIFIED BY nmeaCorrections       } |  
   { ProbeDataManagement   IDENTIFIED BY probeDataManagement   } |
   { ProbeVehicleData      IDENTIFIED BY probeVehicleData      } |  
   { RoadSideAlert         IDENTIFIED BY roadSideAlert         } |      
   { RTCMcorrections       IDENTIFIED BY rtcmCorrections       } |       
   { SignalRequestMessage  IDENTIFIED BY signalRequestMessage  } |    
   { SignalStatusMessage   IDENTIFIED BY signalStatusMessage   } |  
   { TravelerInformation   IDENTIFIED BY travelerInformation   } |  
   { PersonalSafetyMessage IDENTIFIED BY personalSafetyMessage } |  
   { TestMessage00         IDENTIFIED BY testMessage00 } |
   { TestMessage01         IDENTIFIED BY testMessage01 } | 
   { TestMessage02         IDENTIFIED BY testMessage02 } |  
   { TestMessage03         IDENTIFIED BY testMessage03 } | 
   { TestMessage04         IDENTIFIED BY testMessage04 } |     
   { TestMessage05         IDENTIFIED BY testMessage05 } | 
   { TestMessage06         IDENTIFIED BY testMessage06 } |   
   { TestMessage07         IDENTIFIED BY testMessage07 } |    
   { TestMessage08         IDENTIFIED BY testMessage08 } |   
   { TestMessage09         IDENTIFIED BY testMessage09 } |  
   { TestMessage10         IDENTIFIED BY testMessage10 } |
   { TestMessage11         IDENTIFIED BY testMessage11 } | 
   { TestMessage12         IDENTIFIED BY testMessage12 } | 
   { TestMessage13         IDENTIFIED BY testMessage13 } |
   { TestMessage14         IDENTIFIED BY testMessage14 } |  
   { TestMessage15         IDENTIFIED BY testMessage15 } ,
   ... -- Expansion to be used only by the SAE J2735 DSRC TC
   }


-- Regional extensions support
REG-EXT-ID-AND-TYPE ::= CLASS {
   &id     RegionId UNIQUE,
   &Type
   } WITH SYNTAX {&Type IDENTIFIED BY &id}

RegionalExtension {REG-EXT-ID-AND-TYPE : Set} ::= SEQUENCE {
   regionId     REG-EXT-ID-AND-TYPE.&id( {Set} ),
   regExtValue  REG-EXT-ID-AND-TYPE.&Type( {Set}{@regionId} )
   }
 
 
 
-- MSG_NMEAcorrections  (NMEA) (Desc Name) Record 7
NMEAcorrections ::=  SEQUENCE {
   timeStamp MinuteOfTheYear    OPTIONAL,
   rev       NMEA-Revision      OPTIONAL,
             -- the specific edition of the standard
             -- that is being sent, normally 2.0
   msg       NMEA-MsgType       OPTIONAL,
             -- the message and sub-message type, as
             -- defined in the revision being used
   -- NOTE The message type is also in the payload expressed as a string, 
   wdCount   ObjectCount        OPTIONAL,
             -- a count of octets to follow
             -- observe that not all NMEA sentences are limited to 82 characters 
   payload   NMEA-Payload, 
   regional  RegionalExtension {{REGION.Reg-NMEAcorrections}} OPTIONAL,
   ...
   }
 
 
 
-- MSG_PersonalSafetyMessage (PSM) (Desc Name) Record 8
PersonalSafetyMessage ::=  SEQUENCE {
   -- Part I, Sent at all times with each message
   basicType           PersonalDeviceUserType,  
   secMark             DSecond,  
   msgCnt              MsgCount,  
   id                  TemporaryID,
   position            Position3D, --  Lat, Long, Elevation     
   accuracy            PositionalAccuracy,  
   speed               Velocity,
   heading             Heading,               
   accelSet            AccelerationSet4Way,  
 
   -- Part II Content
   pathHistory         PathHistory                OPTIONAL, 
   pathPrediction      PathPrediction             OPTIONAL,
   motorType           MotorizationType           OPTIONAL,
   onWheels            PersonalOnWheelType        OPTIONAL,
   useState            PersonalDeviceUsageState   OPTIONAL,
   motionState         PersonalMovementState      OPTIONAL,
   crossRequest        PersonalCrossingRequest    OPTIONAL,
   crossState          PersonalCrossingInProgress OPTIONAL,
   clusterSize         PersonalClusterSize        OPTIONAL,
   clusterRadius       PersonalClusterRadius      OPTIONAL,
   eventResponderType  PublicSafetyEventResponderType      OPTIONAL,
   activityType        PublicSafetyAndRoadWorkerActivity   OPTIONAL,
   activitySubType     PublicSafetyDirectingTrafficSubType OPTIONAL,
   disability          DisabilityType             OPTIONAL,
   ageGroup            AgeGroup                   OPTIONAL,
   attachment          Attachment                 OPTIONAL,
   attachmentRadius    AttachmentRadius           OPTIONAL,
   animalType          AnimalType                 OPTIONAL,

   regional RegionalExtension {{REGION.Reg-PersonalSafetyMessage}} OPTIONAL,
   ...
   }
 
 
 
-- MSG_ProbeDataManagement  (PDM) (Desc Name) Record 9
ProbeDataManagement ::=  SEQUENCE {
   timeStamp            MinuteOfTheYear OPTIONAL, 
   sample               Sample,           -- Identifies the vehicle  
                                          -- population affected by this
   directions           HeadingSlice,     -- Applicable headings/directions
   term CHOICE {                          
      termtime          TermTime,         -- Terminate this management process 
                                          -- based on Time-to-Live
      termDistance      TermDistance      -- Terminate management process 
                                          -- based on Distance-to-Live
      },
   snapshot CHOICE {
      snapshotTime      SnapshotTime,     -- Collect snapshots based on Time
                                          -- the value 0 indicates forever
      snapshotDistance  SnapshotDistance  -- Collect snapshots based on combination 
                                          -- of vehicle Speed and Distance
      },
   txInterval           SecondOfTime,     -- Time Interval at which to send snapshots
   dataElements         VehicleStatusRequestList OPTIONAL,
                                          -- Control data frames and associated 
                                          -- trigger thresholds to be changed 
   regional             RegionalExtension {{REGION.Reg-ProbeDataManagement}} OPTIONAL,
   ...
   }
 
 
 
-- MSG_ProbeVehicleData  (PVD) (Desc Name) Record 10
ProbeVehicleData ::=  SEQUENCE {
   timeStamp       MinuteOfTheYear OPTIONAL,
   segNum          ProbeSegmentNumber OPTIONAL,   
                                         -- a short term Ident value
                                         -- not used when ident is used
   probeID         VehicleIdent OPTIONAL, 
                                         -- identity data for selected 
                                         -- types of vehicles    
   startVector     FullPositionVector,   -- the space and time of 
                                         -- transmission to the RSU
   vehicleType     VehicleClassification, -- type of vehicle, 
   snapshots       SEQUENCE (SIZE(1..32)) OF Snapshot,               
                                         -- a seq of name-value pairs 
                                         -- along with the space and time 
                                         -- of the first measurement set
   regional        RegionalExtension {{REGION.Reg-ProbeVehicleData}} OPTIONAL,
   ...
   }
 
 
 
-- MSG_RoadSideAlert  (RSA) (Desc Name) Record 11
RoadSideAlert ::=  SEQUENCE { 
   msgCnt        MsgCount,   
   timeStamp     MinuteOfTheYear  OPTIONAL,
   typeEvent     ITIS.ITIScodes,
                 -- a category and an item from that category 
                 -- all ITS stds use the same types here
                 -- to explain the type of  the 
                 -- alert / danger / hazard involved
   description   SEQUENCE (SIZE(1..8)) OF ITIS.ITIScodes OPTIONAL,
                 -- up to eight ITIS code set entries to further
                 -- describe the event, give advice, or any 
                 -- other ITIS codes
   priority      Priority OPTIONAL,  
                 -- the urgency of this message, a relative
                 -- degree of merit compared with other 
                 -- similar messages for this type (not other
                 -- messages being sent by the device), nor a 
                 -- priority of display urgency
   heading       HeadingSlice  OPTIONAL,       
                 -- Applicable headings/direction
   extent        Extent OPTIONAL,  
                 -- the spatial distance over which this
                 -- message applies and should be presented 
                 -- to the driver
   position      FullPositionVector OPTIONAL, 
                 -- a compact summary of the position,
                 -- heading, rate of speed, etc. of the 
                 -- event in question. Including stationary
                 -- and wide area events. 
   furtherInfoID FurtherInfoID OPTIONAL,
                 -- an index link to any other incident 
                 -- information data that may be available 
                 -- in the normal ATIS incident description 
                 -- or other messages
                 -- 1~2 octets in length
   regional      RegionalExtension {{REGION.Reg-RoadSideAlert}} OPTIONAL,
   ...
   }
 
 
 
-- MSG_RTCMcorrections  (RTCM) (Desc Name) Record 12
RTCMcorrections ::=  SEQUENCE {
   msgCnt      MsgCount, 
   rev         RTCM-Revision,
               -- the specific edition of the standard
               -- that is being sent
   timeStamp   MinuteOfTheYear  OPTIONAL,

   -- Observer position, if needed
   anchorPoint FullPositionVector OPTIONAL,
   -- Precise ant position and noise data for a rover
   rtcmHeader  RTCMheader OPTIONAL,  
                    
   -- one or more RTCM messages
   msgs        RTCMmessageList,
   regional    RegionalExtension {{REGION.Reg-RTCMcorrections}} OPTIONAL,
   ...
   }
 
 
 
-- MSG_SignalRequestMessage  (SRM) (Desc Name) Record 13
SignalRequestMessage ::=  SEQUENCE {    
   timeStamp       MinuteOfTheYear  OPTIONAL,
   second          DSecond,
   sequenceNumber  MsgCount         OPTIONAL,

   requests        SignalRequestList OPTIONAL,
                   -- Request Data for one of more signalized 
                   -- intersections that support SRM dialogs

   requestor       RequestorDescription,
                   -- Requesting Device and other User Data
                   -- contains vehicle ID (if from a vehicle)
                   -- as well as type data and current position
                   -- and may contain additional transit data

   regional        RegionalExtension {{REGION.Reg-SignalRequestMessage}} OPTIONAL,
   ...
   }
 
 
 
-- MSG_SignalStatusMessage  (SSM) (Desc Name) Record 14
SignalStatusMessage ::=  SEQUENCE {
   timeStamp       MinuteOfTheYear  OPTIONAL,
   second          DSecond,
   sequenceNumber  MsgCount         OPTIONAL,            

   -- Status Data for one of more signalized intersections
   status          SignalStatusList,
 
   regional        RegionalExtension {{REGION.Reg-SignalStatusMessage}} OPTIONAL,
   ...
   }
 
 
 
-- MSG_SignalPhaseAndTiming Message  (SPAT) (Desc Name) Record 15
SPAT ::=  SEQUENCE { 
   timeStamp     MinuteOfTheYear OPTIONAL,  
   name          DescriptiveName OPTIONAL, 
                 -- human readable name for this collection 
                 -- to be used only in debug mode
   
   intersections IntersectionStateList,
                 -- sets of SPAT data (one per intersection)  
   
   -- If PrioritizationResponse data is required, it is found 
   -- in the RegionalSPAT entry below
   
   regional      RegionalExtension {{REGION.Reg-SPAT}} OPTIONAL,
   ...
   }
 
 
 
-- MSG_TestMessages (Desc Name) Record 16
TestMessage00 ::=  SEQUENCE {
   header    Header   OPTIONAL,
   -- All content is added in below data frame
   regional  RegionalExtension {{REGION.Reg-TestMessage00}} OPTIONAL,
   ...
   }
TestMessage01 ::= SEQUENCE {
   header    Header   OPTIONAL,
   regional  RegionalExtension {{REGION.Reg-TestMessage01}} OPTIONAL,
   ...
   }
TestMessage02 ::= SEQUENCE {
   header    Header   OPTIONAL,
   regional  RegionalExtension {{REGION.Reg-TestMessage02}} OPTIONAL,
   ...  
   }
TestMessage03 ::= SEQUENCE {
   header    Header   OPTIONAL,
   regional  RegionalExtension {{REGION.Reg-TestMessage03}} OPTIONAL,
   ...  
   }
TestMessage04 ::= SEQUENCE {
   header    Header   OPTIONAL,
   regional  RegionalExtension {{REGION.Reg-TestMessage04}} OPTIONAL,
   ...  
   }
TestMessage05 ::= SEQUENCE {
   header    Header   OPTIONAL,
   regional  RegionalExtension {{REGION.Reg-TestMessage05}} OPTIONAL,
   ...  
   }
TestMessage06 ::= SEQUENCE {
   header    Header   OPTIONAL,
   regional  RegionalExtension {{REGION.Reg-TestMessage06}} OPTIONAL,
   ...  
   }
TestMessage07 ::= SEQUENCE {
   header    Header   OPTIONAL,
   regional  RegionalExtension {{REGION.Reg-TestMessage07}} OPTIONAL,
   ...  
   }
TestMessage08 ::= SEQUENCE {
   header    Header   OPTIONAL,
   regional  RegionalExtension {{REGION.Reg-TestMessage08}} OPTIONAL,
   ...  
   }
TestMessage09 ::= SEQUENCE {
   header    Header   OPTIONAL,
   regional  RegionalExtension {{REGION.Reg-TestMessage09}} OPTIONAL,
   ...  
   }
TestMessage10 ::= SEQUENCE {
   header    Header   OPTIONAL,
   regional  RegionalExtension {{REGION.Reg-TestMessage10}} OPTIONAL,
   ...  
   }
TestMessage11 ::= SEQUENCE {
   header    Header   OPTIONAL,
   regional  RegionalExtension {{REGION.Reg-TestMessage11}} OPTIONAL,
   ...  
   }
TestMessage12 ::= SEQUENCE {
   header    Header   OPTIONAL,
   regional  RegionalExtension {{REGION.Reg-TestMessage12}} OPTIONAL,
   ...  
   }
TestMessage13 ::= SEQUENCE {
   header    Header   OPTIONAL,
   regional  RegionalExtension {{REGION.Reg-TestMessage13}} OPTIONAL,
   ...  
   }
TestMessage14 ::= SEQUENCE {
   header    Header   OPTIONAL,
   regional  RegionalExtension {{REGION.Reg-TestMessage14}} OPTIONAL,
   ...  
   }
TestMessage15 ::= SEQUENCE {
   header    Header   OPTIONAL,
   regional  RegionalExtension {{REGION.Reg-TestMessage15}} OPTIONAL,
   ...  
   }
 
 
 
-- MSG_TravelerInformation Message  (TIM) (Desc Name) Record 17
TravelerInformation ::=  SEQUENCE {
   msgCnt      MsgCount,  
   timeStamp   MinuteOfTheYear OPTIONAL,
   packetID    UniqueMSGID     OPTIONAL,    
   urlB        URL-Base        OPTIONAL,  

   -- A set of one or more self contained 
   -- traveler information messages (frames)
   dataFrames  TravelerDataFrameList,
 
   regional    RegionalExtension {{REGION.Reg-TravelerInformation}} OPTIONAL,
   ...
   }
 
 
-- -_-_-_-_-_-_-_-_-_-_-_-_-_-_-_-_-_-_-_-_-_-_-_-_-_-_-_-_
-- 
-- Start of entries from table Data_Frames...
-- This table typicaly contains data frame entries.
-- -_-_-_-_-_-_-_-_-_-_-_-_-_-_-_-_-_-_-_-_-_-_-_-_-_-_-_-_
-- 
 
 
-- DF_AccelerationSet4Way (Desc Name) Record 1
AccelerationSet4Way ::=  SEQUENCE {
   long Acceleration,          -- Along the Vehicle Longitudinal axis
   lat  Acceleration,          -- Along the Vehicle Lateral axis
   vert VerticalAcceleration,  -- Along the Vehicle Vertical axis
   yaw  YawRate
}
 
 
 
-- DF_AccelSteerYawRateConfidence (Desc Name) Record 2
AccelSteerYawRateConfidence ::=  SEQUENCE {
   yawRate             YawRateConfidence, 
   acceleration        AccelerationConfidence, 
   steeringWheelAngle  SteeringWheelAngleConfidence 
   }
 
 
 
-- DF_AdvisorySpeed (Desc Name) Record 3
AdvisorySpeed ::=  SEQUENCE {
   type        AdvisorySpeedType,
               -- the type of advisory which this is.
   speed       SpeedAdvice OPTIONAL,
               -- See Section 11 for converting and tranlating speed 
               -- expressed in MPH into units of m/s
               -- This element is optional ONLY when superceded 
               -- by the presence of a regional speed element found in
               -- Reg-AdvisorySpeed entry
   confidence  SpeedConfidence OPTIONAL,
               -- A confidence value for the above speed
   distance    ZoneLength OPTIONAL,
               -- Unit = 1 meter,  
               -- The distance indicates the region for which the advised speed 
               -- is recommended, it is specified upstream from the stop bar  
               -- along the connected egressing lane
   class       RestrictionClassID OPTIONAL,
               -- the vehicle types to which it applies
               -- when absent, the AdvisorySpeed applies to
               -- all motor vehicle types
   regional    RegionalExtension {{REGION.Reg-AdvisorySpeed}} OPTIONAL,
   ...
   }
 
 
 
-- DF_AdvisorySpeedList (Desc Name) Record 4
AdvisorySpeedList ::=  SEQUENCE (SIZE(1..16)) OF AdvisorySpeed
 
 
 
-- DF_AntennaOffsetSet (Desc Name) Record 5
AntennaOffsetSet ::=  SEQUENCE { 
   antOffsetX  Offset-B12, -- a range of +- 20.47 meters
   antOffsetY  Offset-B09, -- a range of +- 2.55 meters
   antOffsetZ  Offset-B10  -- a range of +- 5.11 meters
   }
 
 
 
-- DF_ApproachOrLane (Desc Name) Record 6
ApproachOrLane ::=  CHOICE {
   approach   ApproachID,
   lane       LaneID
   }
 
 
 
-- DF_BrakeSystemStatus (Desc Name) Record 7
BrakeSystemStatus ::=  SEQUENCE { 
   wheelBrakes        BrakeAppliedStatus,
   traction           TractionControlStatus,
   abs                AntiLockBrakeStatus, 
   scs                StabilityControlStatus,
   brakeBoost         BrakeBoostApplied, 
   auxBrakes          AuxiliaryBrakeStatus
   }
 
 
 
-- DF_BSMcoreData (Desc Name) Record 8
BSMcoreData ::=  SEQUENCE {   
   secMark       DSecond,  
   msgCnt        MsgCount,  
   id            TemporaryID,
   lat           Latitude,              
   long          Longitude,             
   elev          Elevation,             
   accuracy      PositionalAccuracy,    
   transmisson   TransmissionState,
   speed         Speed,
   heading       Heading,               
   angle         SteeringWheelAngle,    
   accelSet      AccelerationSet4Way,   
   brakes        BrakeSystemStatus,     
   size          VehicleSize          
   }
 
 
 
-- DF_BumperHeights (Desc Name) Record 9
BumperHeights ::=  SEQUENCE {
   front      BumperHeight, 
   rear       BumperHeight
   }
 
 
 
-- DF_Circle (Desc Name) Record 10
Circle ::=  SEQUENCE {
   center   Position3D,
   radius   Radius-B12, 
   units    DistanceUnits
   }
 
 
 
-- DF_ComputedLane (Desc Name) Record 11
ComputedLane ::=  SEQUENCE {
   -- Data needed to created a computed lane
   referenceLaneId    LaneID,
                         -- the lane ID upon which this 
                         -- computed lane will be based 
   -- Lane Offset in X and Y direction
   offsetXaxis        CHOICE {
                         small   DrivenLineOffsetSm, 
                         large   DrivenLineOffsetLg
                         },  
   offsetYaxis        CHOICE {
                         small   DrivenLineOffsetSm, 
                         large   DrivenLineOffsetLg
                         },  
                         -- An path X offset value for translations of the 
                         -- path's points when created translated lanes. 
                         -- The values found in the reference lane are 
                         -- all offset based on the X and Y values from 
                         -- the coordinates of the reference lane's 
                         -- starting initial point.   
   -- Lane Rotation
   rotateXY           Angle OPTIONAL, 
                         -- A path rotation value for the entire lane
                         -- Observe that this rotates the existing orientation 
                         -- of the referenced lane, it does not replace it.
   -- Lane Path Scale (zooming)
   scaleXaxis         Scale-B12 OPTIONAL, 
   scaleYaxis         Scale-B12 OPTIONAL, 
                         -- value for translations or zooming of the path's 
                         -- points. The values found in the reference lane 
                         -- are all expanded of contracted based on the X 
                         -- and Y and width values from the coordinates of 
                         -- the reference lane's starting initial point.  
                         -- The Z axis remains untouched.  
   regional  RegionalExtension {{REGION.Reg-ComputedLane}} OPTIONAL,
   ... 
   }
 
 
 
-- DF_ConfidenceSet (Desc Name) Record 12
ConfidenceSet ::=  SEQUENCE {
   accelConfidence      AccelSteerYawRateConfidence OPTIONAL,    
   speedConfidence      SpeedandHeadingandThrottleConfidence OPTIONAL,      
   timeConfidence       TimeConfidence OPTIONAL,           
   posConfidence        PositionConfidenceSet OPTIONAL,           
   steerConfidence      SteeringWheelAngleConfidence OPTIONAL,
   headingConfidence    HeadingConfidence OPTIONAL,
   throttleConfidence   ThrottleConfidence OPTIONAL,
   ...  
   }
 
 
 
-- DF_ConnectingLane (Desc Name) Record 13
ConnectingLane ::=  SEQUENCE {
   lane      LaneID,   -- Index of the connecting lane
   maneuver  AllowedManeuvers OPTIONAL
                       -- The Maneuver between 
                       -- the enclosing lane and this lane
                       -- at the stop line to connect them
   }
 
 
 
-- DF_Connection (Desc Name) Record 14
Connection ::=  SEQUENCE {
   -- The subject lane connecting to this lane is:
   connectingLane     ConnectingLane, 
                      -- The index of the connecting lane and also
                      -- the maneuver from the current lane to it
   remoteIntersection IntersectionReferenceID OPTIONAL,  
                      -- This entry is only used when the 
                      -- indicated connecting lane belongs 
                      -- to another intersection layout. This 
                      -- provides a means to create meshes of lanes
   
   -- SPAT mapping details at the stop line are:
   signalGroup        SignalGroupID OPTIONAL,    
                      -- The matching signal group send by 
                      -- the SPAT message for this lane/maneuver
                      -- Shall be present unless the connectingLane 
                      -- has not signal group (is un-signalized)
   userClass          RestrictionClassID OPTIONAL, 
                      -- The Restriction Class of users this applies to
                      -- The use of some lane/maneuver and SignalGroupID 
                      -- pairings are restricted to selected users
                      -- when absent, the SignalGroupID applies to all
   
   -- Movement assist details are given by:
   connectionID       LaneConnectionID OPTIONAL
                      -- An optional connection index used to 
                      -- relate this lane connection to any dynamic 
                      -- clearance data in the SPAT. Note that
                      -- the index may be shared with other 
                      -- connections if the clearance data is common
   }
 
 
 
-- DF_ConnectionManeuverAssist (Desc Name) Record 15
ConnectionManeuverAssist ::=  SEQUENCE {
   connectionID         LaneConnectionID,
                        -- the common connectionID used by all lanes to which
                        -- this data applies 
                        -- (this value traces to ConnectsTo entries in lanes)
   -- Expected Clearance Information
   queueLength          ZoneLength OPTIONAL,
                        -- Unit = 1 meter, 0 = no queue
                        -- The distance from the stop line to the back 
                        -- edge of the last vehicle in the queue,                     
                        -- as measured along the lane center line.
   availableStorageLength ZoneLength OPTIONAL,
                        -- Unit = 1 meter, 0 = no space remains
                        -- Distance (e.g. beginning from the downstream 
                        -- stop-line up to a given distance) with a high 
                        -- probability for successfully executing the 
                        -- connection maneuver between the two lanes 
                        -- during the current cycle. 
                        -- Used for enhancing the awareness of vehicles 
                        -- to anticipate if they can pass the stop line
                        -- of the lane. Used for optimizing the green wave, 
                        -- due to knowledge of vehicles waiting in front 
                        -- of a red light (downstream).
                        -- The element nextTime in TimeChangeDetails
                        -- in the containing data frame contains the next 
                        -- timemark at which an active phase is expected, 
                        -- a form of storage flush interval.
   waitOnStop           WaitOnStopline OPTIONAL,
                        -- If "true", the vehicles on this specific connecting 
                        -- maneuver have to stop on the stop-line and not 
                        -- to enter the collision area 
   pedBicycleDetect     PedestrianBicycleDetect OPTIONAL,
                        -- true if ANY ped or bicycles are detected crossing 
                        -- the above lanes. Set to false ONLY if there is a 
                        -- high certainty that there are none present, 
                        -- otherwise element is not sent.
   regional  RegionalExtension {{REGION.Reg-ConnectionManeuverAssist}} OPTIONAL,
   ...  
   }
 
 
 
-- DF_ConnectsToList (Desc Name) Record 16
ConnectsToList ::=  SEQUENCE (SIZE(1..16)) OF Connection
 
 
 
-- DF_DataParameters (Desc Name) Record 17
DataParameters ::=  SEQUENCE {
   processMethod     IA5String(SIZE(1..255)) OPTIONAL, 
   processAgency     IA5String(SIZE(1..255)) OPTIONAL, 
   lastCheckedDate   IA5String(SIZE(1..255)) OPTIONAL, 
   geoidUsed         IA5String(SIZE(1..255)) OPTIONAL, 
   ...  
   }
 
 
 
-- DF_DDate (Desc Name) Record 18
DDate ::=  SEQUENCE {
   year    DYear,       
   month   DMonth,   
   day     DDay    
   }
 
 
 
-- DF_DDateTime (Desc Name) Record 19
DDateTime ::=  SEQUENCE {
   year    DYear    OPTIONAL,    
   month   DMonth   OPTIONAL,   
   day     DDay     OPTIONAL,  
   hour    DHour    OPTIONAL,   
   minute  DMinute  OPTIONAL,  
   second  DSecond  OPTIONAL,  
   offset  DOffset  OPTIONAL -- time zone
   }
 
 
 
-- DF_DFullTime (Desc Name) Record 20
DFullTime ::=  SEQUENCE {
   year    DYear,      
   month   DMonth,      
   day     DDay,    
   hour    DHour,  
   minute  DMinute   
   }
 
 
 
-- DF_DMonthDay (Desc Name) Record 21
DMonthDay ::=  SEQUENCE {
   month   DMonth,   
   day     DDay       
   }
 
 
 
-- DF_DTime (Desc Name) Record 22
DTime ::=  SEQUENCE {
   hour    DHour,        
   minute  DMinute,         
   second  DSecond,          
   offset  DOffset  OPTIONAL -- time zone
   }
 
 
 
-- DF_DYearMonth (Desc Name) Record 23
DYearMonth ::=  SEQUENCE {
   year    DYear,       
   month   DMonth         
   }
 
 
 
-- DF_EmergencyDetails (Desc Name) Record 24
EmergencyDetails ::=  SEQUENCE {
   -- CERT SSP Privilege Details
   sspRights    SSPindex, -- index set by CERT
   sirenUse     SirenInUse,                 
   lightsUse    LightbarInUse,              
   multi        MultiVehicleResponse,
   events       PrivilegedEvents OPTIONAL,
   responseType ResponseType OPTIONAL,
   ...
   }
 
 
 
-- DF_EnabledLaneList (Desc Name) Record 25
EnabledLaneList ::=  SEQUENCE (SIZE(1..16)) OF LaneID
   -- The unique ID numbers for each
   -- lane object which is 'active' 
   -- as part of the dynamic map contents.
 
 
 
-- DF_EventDescription (Desc Name) Record 26
EventDescription ::=  SEQUENCE {
   typeEvent     ITIS.ITIScodes,
                 -- a category and an item from that category 
                 -- all ITS stds use the same types here
                 -- to explain the type of  the 
                 -- alert / danger / hazard involved
   description   SEQUENCE (SIZE(1..8)) OF ITIS.ITIScodes OPTIONAL,
                 -- up to eight ITIS code set entries to further
                 -- describe the event, give advice, or any 
                 -- other ITIS codes
   priority      Priority OPTIONAL,  
                 -- the urgency of this message, a relative
                 -- degree of merit compared with other 
                 -- similar messages for this type (not other
                 -- messages being sent by the device), nor a 
                 -- priority of display urgency
   heading       HeadingSlice  OPTIONAL,       
                 -- Applicable headings/direction
   extent        Extent OPTIONAL,  
                 -- the spatial distance over which this
                 -- message applies and should be presented to the driver
   regional      RegionalExtension {{REGION.Reg-EventDescription}} OPTIONAL,
   ...
   }
 
 
 
-- DF_ITIS_Phrase_ExitService (Desc Name) Record 27
ExitService ::=  SEQUENCE (SIZE(1..16)) OF SEQUENCE {
  item CHOICE    {
       itis   ITIS.ITIScodes,
       text   ITIStextPhrase
       }  
  }
 
 
 
-- DF_FullPositionVector (Desc Name) Record 28
FullPositionVector ::=  SEQUENCE {
   utcTime             DDateTime OPTIONAL,   -- time with mSec precision
   long                Longitude,            -- 1/10th microdegree
   lat                 Latitude,             -- 1/10th microdegree
   elevation           Elevation  OPTIONAL,  -- units of 0.1 m
   heading             Heading OPTIONAL, 
   speed               TransmissionAndSpeed OPTIONAL,
   posAccuracy         PositionalAccuracy OPTIONAL,
   timeConfidence      TimeConfidence OPTIONAL,
   posConfidence       PositionConfidenceSet OPTIONAL,
   speedConfidence     SpeedandHeadingandThrottleConfidence OPTIONAL, 
   ...  
   }
 
 
 
-- DF_GenericLane (Desc Name) Record 29
GenericLane ::=  SEQUENCE { 
   laneID           LaneID, 
                    -- The unique ID number assigned 
                    -- to this lane object
   name             DescriptiveName OPTIONAL,        
                    -- often for debug use only 
                    -- but at times used to name ped crossings
   ingressApproach  ApproachID OPTIONAL, -- inbound
   egressApproach   ApproachID OPTIONAL, -- outbound
                    -- Approach IDs to which this lane belongs
   laneAttributes   LaneAttributes, 
                    -- All Attribute information about 
                    -- the basic selected lane type
                    -- Directions of use, Geometric co-sharing
                    -- and Type Specific Attributes
                    -- These Attributes are 'lane - global' that is,
                    -- they are true for the entire length of the lane
   maneuvers        AllowedManeuvers OPTIONAL,
                    -- the permitted maneuvers for this lane
   nodeList         NodeListXY,
                    -- Lane spatial path information as well as
                    -- various Attribute information along the node path  
                    -- Attributes found here are more general and may
                    -- come and go over the length of the lane.
   connectsTo       ConnectsToList OPTIONAL, 
                    -- a list of other lanes and their signal group IDs
                    -- each connecting lane and its signal group ID
                    -- is given, therefore this element provides the
                    -- information formally in "signalGroups" in prior
                    -- editions.
   overlays         OverlayLaneList OPTIONAL, 
                    -- A list of any lanes which have spatial paths that
                    -- overlay (run on top of, and not simply cross) 
                    -- the path of this lane when used
   regional  RegionalExtension {{REGION.Reg-GenericLane}} OPTIONAL,
   ...
   }
 
 
 
-- DF_ITIS_Phrase_GenericSignage (Desc Name) Record 30
GenericSignage ::=  SEQUENCE (SIZE(1..16)) OF SEQUENCE {
  item CHOICE    {
       itis   ITIS.ITIScodes,
       text   ITIStextPhrase
       }  
  }
 
 
 
-- DF_GeographicalPath (Desc Name) Record 31
GeographicalPath ::=  SEQUENCE {
   name             DescriptiveName          OPTIONAL,
   id               RoadSegmentReferenceID   OPTIONAL,
   anchor           Position3D               OPTIONAL, 
   laneWidth        LaneWidth                OPTIONAL, 
   directionality   DirectionOfUse           OPTIONAL, 
   closedPath       BOOLEAN                  OPTIONAL, 
                    -- when true, last point closes to first
   direction        HeadingSlice             OPTIONAL, 
                    -- field of view over which this applies
   description CHOICE  {
      path         OffsetSystem,
                   -- The XYZ and LLH system of paths
      geometry     GeometricProjection,
                   -- A projected circle from a point
      oldRegion    ValidRegion,  
                   -- Legacy method, no longer recommended for use
      ...
      } OPTIONAL,
   
   regional     RegionalExtension {{REGION.Reg-GeographicalPath}} OPTIONAL,
   ...  
   }
 
 
 
-- DF_GeometricProjection (Desc Name) Record 32
GeometricProjection ::=  SEQUENCE {
   direction        HeadingSlice,
                    -- field of view over which this applies,
   extent           Extent OPTIONAL,  
                    -- the spatial distance over which this
                    -- message applies and should be presented
   laneWidth        LaneWidth OPTIONAL, -- used when a width is needed
   circle           Circle, -- A point and radius

   -- TBD details pending TIM needs review

   regional         RegionalExtension {{REGION.Reg-GeometricProjection}} OPTIONAL,
   ...  
   }
 
 
 
-- DF_Header (Desc Name) Record 33
Header ::=  SEQUENCE {
   -- Basic time and sequence values for the message
   year              DYear           OPTIONAL,
   timeStamp         MinuteOfTheYear OPTIONAL, 
   secMark           DSecond         OPTIONAL, 
   msgIssueRevision  MsgCount        OPTIONAL,         
   ...  
   }
 
 
 
-- DF_IntersectionAccessPoint (Desc Name) Record 34
IntersectionAccessPoint ::=  CHOICE {
   lane       LaneID,
   approach   ApproachID,
   connection LaneConnectionID,
   ...
   }
 
 
 
-- DF_IntersectionGeometry (Desc Name) Record 35
IntersectionGeometry ::=  SEQUENCE {
   name        DescriptiveName OPTIONAL, 
                            -- For debug use only
   id          IntersectionReferenceID,  
                            -- A globally unique value set, 
                            -- consisting of a regionID and 
                            -- intersection ID assignment
   revision    MsgCount,    

   -- Required default values about lane descriptions follow
   refPoint    Position3D,  -- The reference from which subsequent 
                            -- data points are offset until a new
                            -- point is used. 
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given 
                            -- See Section 11 for converting and 
                            -- tranlating speed expressed in MPH 
                            -- into units of m/s
   -- Complete details regarding each lane type in this intersection
   laneSet     LaneList,    -- Data about one or more lanes
                            -- (all lane data is found here)
   
   -- Data describing how to use and request preemption and
   -- priority services from this intersection (if supported)
   -- NOTE Additonal data may be added in the next release of the 
   -- standard at this point to handle this concept
   preemptPriorityData PreemptPriorityList OPTIONAL, 
                           -- data about one or more regional
                           -- preempt or priority zones 
   
   regional     RegionalExtension {{REGION.Reg-IntersectionGeometry}} OPTIONAL,
   ... 
   }
 
 
 
-- DF_IntersectionGeometryList (Desc Name) Record 36
IntersectionGeometryList ::=  SEQUENCE (SIZE(1..32)) OF IntersectionGeometry
 
 
 
-- DF_IntersectionReferenceID (Desc Name) Record 37
IntersectionReferenceID ::=  SEQUENCE {
   region  RoadRegulatorID OPTIONAL,
           -- a globally unique regional assignment value
           -- typical assigned to a regional DOT authority
           -- the value zero shall be used for testing needs
   id      IntersectionID
           -- a unique mapping to the intersection
           -- in question within the above region of use
   }
 
 
 
-- DF_IntersectionState (Desc Name) Record 38
IntersectionState ::=  SEQUENCE {
   name         DescriptiveName OPTIONAL, 
                -- human readable name for intersection  
                -- to be used only in debug mode
   id           IntersectionReferenceID,  
                -- A globally unique value set, consisting of a 
                -- regionID and intersection ID assignment
                -- provides a unique mapping to the 
                -- intersection MAP in question
                -- which provides complete location 
                -- and approach/move/lane data
   revision     MsgCount,    
   status       IntersectionStatusObject,
                -- general status of the controller(s)
   moy          MinuteOfTheYear OPTIONAL,
                -- Minute of current UTC year
                -- used only with messages to be archived 
   timeStamp    DSecond OPTIONAL, 
                -- the mSec point in the current UTC minute that
                -- this message was constructed
   enabledLanes EnabledLaneList OPTIONAL,  
                -- a list of lanes where the RevocableLane bit 
                -- has been set which are now active and 
                -- therefore part of the current intersection
   states       MovementList,
                -- Each Movement is given in turn
                -- and contains its signal phase state, 
                -- mapping to the lanes it applies to, and
                -- point in time it will end, and it
                -- may contain both active and future states 
   maneuverAssistList  ManeuverAssistList OPTIONAL,
                -- Assist data
   priority     SignalControlState OPTIONAL,
                -- the active priority state data, if present
   preempt      SignalControlState OPTIONAL,
                -- the active preemption state data, if present
   
   regional     RegionalExtension {{REGION.Reg-IntersectionState}} OPTIONAL,
   ... 
   }
 
 
 
-- DF_IntersectionStateList (Desc Name) Record 39
IntersectionStateList ::=  SEQUENCE (SIZE(1..32)) OF  IntersectionState
 
 
 
-- DF_J1939-Data Items (Desc Name) Record 40
J1939data ::=  SEQUENCE {
   -- Tire conditions by tire
   tires                    TireDataList              OPTIONAL,
   -- Vehicle Weights by axle
   axles                    AxleWeightList            OPTIONAL,      
   trailerWeight            TrailerWeight             OPTIONAL,     
   cargoWeight              CargoWeight               OPTIONAL, 
   steeringAxleTemperature  SteeringAxleTemperature   OPTIONAL, 
   driveAxleLocation        DriveAxleLocation         OPTIONAL, 
   driveAxleLiftAirPressure DriveAxleLiftAirPressure  OPTIONAL, 
   driveAxleTemperature     DriveAxleTemperature      OPTIONAL, 
   driveAxleLubePressure    DriveAxleLubePressure     OPTIONAL, 
   steeringAxleLubePressure SteeringAxleLubePressure  OPTIONAL, 
   ...
   }   

TireDataList ::= SEQUENCE (SIZE(1..16)) OF TireData 

TireData ::= SEQUENCE {
      location              TireLocation              OPTIONAL, 
      pressure              TirePressure              OPTIONAL, 
      temp                  TireTemp                  OPTIONAL, 
      wheelSensorStatus     WheelSensorStatus         OPTIONAL, 
      wheelEndElectFault    WheelEndElectFault        OPTIONAL, 
      leakageRate           TireLeakageRate           OPTIONAL, 
      detection             TirePressureThresholdDetection OPTIONAL, 
      ...
      }

AxleWeightList ::= SEQUENCE (SIZE(1..16)) OF AxleWeightSet

AxleWeightSet ::= SEQUENCE {
      location              AxleLocation              OPTIONAL, 
      weight                AxleWeight                OPTIONAL, 
      ...
      }
 
 
 
-- DF_LaneAttributes (Desc Name) Record 41
LaneAttributes ::=  SEQUENCE {
   directionalUse  LaneDirection,      -- directions of lane use
   sharedWith      LaneSharing,        -- co-users of the lane path
   laneType        LaneTypeAttributes, -- specific lane type data
   regional        RegionalExtension {{REGION.Reg-LaneAttributes}} OPTIONAL
   }
 
 
 
-- DF_LaneDataAttribute (Desc Name) Record 42
LaneDataAttribute ::=  CHOICE {
    -- Segment attribute types and the data needed for each
    pathEndPointAngle        DeltaAngle,  
                             -- adjusts final point/width slant
                             -- of the lane to align with the stop line
    laneCrownPointCenter     RoadwayCrownAngle,  
                             -- sets the canter of the road bed      
                             -- from centerline point
    laneCrownPointLeft       RoadwayCrownAngle,  
                             -- sets the canter of the road bed
                             -- from left edge
    laneCrownPointRight      RoadwayCrownAngle,  
                             -- sets the canter of the road bed
                             -- from right edge
    laneAngle                MergeDivergeNodeAngle,  
                             -- the angle or direction of another lane
                             -- this is required to support Japan style
                             -- when a merge point angle is required
    speedLimits              SpeedLimitList,
                             -- Reference regulatory speed limits
                             -- used by all segments
   
    -- Add others as needed, in regional space
    regional  RegionalExtension {{REGION.Reg-LaneDataAttribute}}, 
    ...
    }
 
 
 
-- DF_LaneDataAttributeList (Desc Name) Record 43
LaneDataAttributeList ::=  SEQUENCE (SIZE(1..8)) OF LaneDataAttribute
 
 
 
-- DF_LaneList (Desc Name) Record 44
LaneList ::=  SEQUENCE (SIZE(1..255)) OF GenericLane
 
 
 
-- DF_LaneTypeAttributes (Desc Name) Record 45
LaneTypeAttributes ::=  CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   }
 
 
 
-- DF_ManeuverAssistList (Desc Name) Record 46
ManeuverAssistList ::=  SEQUENCE (SIZE(1..16)) OF ConnectionManeuverAssist
 
 
 
-- DF_MovementEvent (Desc Name) Record 47
MovementEvent ::=  SEQUENCE {
   eventState   MovementPhaseState,
                -- Consisting of:
                -- Phase state (the basic 11 states)
                -- Directional, protected, or permissive state
   
   timing       TimeChangeDetails OPTIONAL,
                -- Timing Data in UTC time stamps for event
                -- includes start and min/max end times of phase
                -- confidence and estimated next occurrence
   
   speeds       AdvisorySpeedList OPTIONAL,
                -- various speed advisories for use by
                -- general and specific types of vehicles
                -- supporting green-wave and other flow needs
                -- See Section 11 for converting and tranlating 
                -- speed expressed in MPH into units of m/s

   regional     RegionalExtension {{REGION.Reg-MovementEvent}} OPTIONAL,
   ...  
   }
 
 
 
-- DF_MovementEventList (Desc Name) Record 48
MovementEventList ::=  SEQUENCE (SIZE(1..16)) OF MovementEvent
 
 
 
-- DF_MovementList (Desc Name) Record 49
MovementList ::=  SEQUENCE (SIZE(1..255)) OF MovementState
 
 
 
-- DF_MovementState (Desc Name) Record 50
MovementState ::=  SEQUENCE {
   movementName       DescriptiveName OPTIONAL,
                      -- uniquely defines movement by name   
                      -- human readable name for intersection  
                      -- to be used only in debug mode
   signalGroup        SignalGroupID,    
                      -- the group id is used to map to lists 
                      -- of lanes (and their descriptions) 
                      -- which this MovementState data applies to 
                      -- see comments in the Remarks for usage details 
   state-time-speed   MovementEventList,   
                      -- Consisting of sets of movement data with:
                      -- a)  SignalPhaseState
                      -- b)  TimeChangeDetails,  and 
                      -- c)  AdvisorySpeeds      (optional )
                      -- Note one or more of the movement events may be for 
                      -- a future time and that this allows conveying multiple 
                      -- predictive phase and movement timing for various uses
                      -- for the current signal group
   maneuverAssistList ManeuverAssistList OPTIONAL,
                      -- This information may also be placed in the 
                      -- IntersectionState when common information applies to
                      -- different lanes in the same way
   regional           RegionalExtension {{REGION.Reg-MovementState}} OPTIONAL,
   ...  
   }
 
 
 
-- DF_NodeAttributeLLList (Desc Name) Record 51
NodeAttributeLLList ::=  SEQUENCE (SIZE(1..8)) OF NodeAttributeLL
 
 
 
-- DF_NodeAttributeSetLL (Desc Name) Record 52
NodeAttributeSetLL ::=  SEQUENCE {
   localNode    NodeAttributeLLList OPTIONAL,
                -- Attribute states which pertain to this node point
   disabled     SegmentAttributeLLList OPTIONAL,
                -- Attribute states which are disabled at this node point
   enabled      SegmentAttributeLLList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation 
                -- at this node from this node onwards, in 10cm steps
                -- elevations between nodes are a linear taper between pts
                -- the value of zero shall not be sent here
   regional     RegionalExtension {{REGION.Reg-NodeAttributeSetLL}} OPTIONAL,
   ...
   }
 
 
 
-- DF_NodeAttributeSetXY (Desc Name) Record 53
NodeAttributeSetXY ::=  SEQUENCE {
   localNode    NodeAttributeXYList OPTIONAL,
                -- Attribute states which pertain to this node point
   disabled     SegmentAttributeXYList OPTIONAL,
                -- Attribute states which are disabled at this node point
   enabled      SegmentAttributeXYList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation 
                -- at this node from this node onwards, in 10cm steps
                -- elevations between nodes are a linear taper between pts
                -- the value of zero shall not be sent here
   regional     RegionalExtension {{REGION.Reg-NodeAttributeSetXY}} OPTIONAL,
   ...
   }
 
 
 
-- DF_NodeAttributeXYList (Desc Name) Record 54
NodeAttributeXYList ::=  SEQUENCE (SIZE(1..8)) OF NodeAttributeXY
 
 
 
-- DF_NodeListLL (Desc Name) Record 55
NodeListLL ::=  CHOICE {
   nodes     NodeSetLL,
             -- a path made up of two or more
             -- LL node points and any attributes 
             -- defined in those nodes
   -- Additional choices will be added in time
   ...
   }
 
 
 
-- DF_NodeListXY (Desc Name) Record 56
NodeListXY ::=  CHOICE {
   nodes     NodeSetXY,
             -- a lane made up of two or more
             -- XY node points and any attributes 
             -- defined in those nodes
   computed  ComputedLane,
             -- a lane path computed by translating 
             -- the data defined by another lane
   ...
   }
 
 
 
-- DF_NodeLL (Desc Name) Record 57
NodeLL ::=  SEQUENCE {
   delta       NodeOffsetPointLL,
               -- A choice of which Lat,Lon offset value to use  
               -- this includes various delta values as well a regional choices
   attributes  NodeAttributeSetLL OPTIONAL,
               -- Any optional Attributes which are needed
               -- This includes changes to the current lane width and elevation
   ... 
   }
 
 
 
-- DF_Node_LL_24B (Desc Name) Record 58
Node-LL-24B ::=  SEQUENCE {
   -- ranges of +- 0.0002047 degrees
   -- ranges of +- 22.634554 meters at the equator
   lon  OffsetLL-B12,
   lat  OffsetLL-B12
   }
 
 
 
-- DF_Node_LL_28B (Desc Name) Record 59
Node-LL-28B ::=  SEQUENCE {
   -- ranges of +- 0.0008191 degrees
   -- ranges of +- 90.571389 meters at the equator
   lon  OffsetLL-B14,
   lat  OffsetLL-B14
   }
 
 
 
-- DF_Node_LL_32B (Desc Name) Record 60
Node-LL-32B ::=  SEQUENCE {
   -- ranges of +- 0.0032767 degrees
   -- ranges of +- 362.31873 meters at the equator
   lon  OffsetLL-B16,
   lat  OffsetLL-B16
   }
 
 
 
-- DF_Node_LL_36B (Desc Name) Record 61
Node-LL-36B ::=  SEQUENCE {
   -- ranges of +- 0.0131071 degrees
   -- ranges of +- 01.449308 Kmeters at the equator
   lon  OffsetLL-B18,
   lat  OffsetLL-B18
   }
 
 
 
-- DF_Node_LL_44B (Desc Name) Record 62
Node-LL-44B ::=  SEQUENCE {
   -- ranges of +- 0.2097151 degrees
   -- ranges of +- 23.189096 Kmeters at the equator
   lon  OffsetLL-B22,
   lat  OffsetLL-B22
   }
 
 
 
-- DF_Node_LL_48B (Desc Name) Record 63
Node-LL-48B ::=  SEQUENCE {
   -- ranges of +- 0.8388607 degrees
   -- ranges of +- 92.756481 Kmeters at the equator
   lon  OffsetLL-B24,
   lat  OffsetLL-B24
   }
 
 
 
-- DF_Node_LLmD_64b (Desc Name) Record 64
Node-LLmD-64b ::=  SEQUENCE {
   lon  Longitude,
   lat  Latitude
   }
 
 
 
-- DF_NodeOffsetPoint_LL (Desc Name) Record 65
NodeOffsetPointLL ::=  CHOICE {
   -- Nodes with LL content         Span at the equator when using a zoom of one:
   node-LL1         Node-LL-24B,    -- within +- 22.634554  meters of last node
   node-LL2         Node-LL-28B,    -- within +- 90.571389  meters of last node
   node-LL3         Node-LL-32B,    -- within +- 362.31873  meters of last node
   node-LL4         Node-LL-36B,    -- within +- 01.449308 Kmeters of last node
   node-LL5         Node-LL-44B,    -- within +- 23.189096 Kmeters of last node
   node-LL6         Node-LL-48B,    -- within +- 92.756481 Kmeters of last node
   node-LatLon      Node-LLmD-64b,  -- node is a full 32b Lat/Lon range
   regional         RegionalExtension {{REGION.Reg-NodeOffsetPointLL}}
                                    -- node which follows is of a
                                    -- regional definition type
   }
 
 
 
-- DF_NodeOffsetPointXY (Desc Name) Record 66
NodeOffsetPointXY ::=  CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   regional         RegionalExtension {{REGION.Reg-NodeOffsetPointXY}}
                                    -- node which follows is of a 
                                    -- regional definition type 
   }
 
 
 
-- DF_NodeSetLL (Desc Name) Record 67
NodeSetLL ::=  SEQUENCE (SIZE(2..63)) OF NodeLL
 
 
 
-- DF_NodeSetXY (Desc Name) Record 68
NodeSetXY ::=  SEQUENCE (SIZE(2..63)) OF NodeXY
 
 
 
-- DF_NodeXY (Desc Name) Record 69
NodeXY ::=  SEQUENCE {
   delta       NodeOffsetPointXY,
               -- A choice of which X,Y offset value to use  
               -- this includes various delta values as well a regional choices
   attributes  NodeAttributeSetXY OPTIONAL,
               -- Any optional Attributes which are needed
               -- This includes changes to the current lane width and elevation
   ... 
   }
 
 
 
-- DF_Node_XY_20b (Desc Name) Record 70
Node-XY-20b ::=  SEQUENCE {
   x  Offset-B10,
   y  Offset-B10
   }
 
 
 
-- DF_Node_XY_22b (Desc Name) Record 71
Node-XY-22b ::=  SEQUENCE {
   x  Offset-B11,
   y  Offset-B11
   }
 
 
 
-- DF_Node_XY_24b (Desc Name) Record 72
Node-XY-24b ::=  SEQUENCE {
   x  Offset-B12,
   y  Offset-B12
   }
 
 
 
-- DF_Node_XY_26b (Desc Name) Record 73
Node-XY-26b ::=  SEQUENCE {
   x  Offset-B13,
   y  Offset-B13
   }
 
 
 
-- DF_Node_XY_28b (Desc Name) Record 74
Node-XY-28b ::=  SEQUENCE {
   x  Offset-B14,
   y  Offset-B14
   }
 
 
 
-- DF_Node_XY_32b (Desc Name) Record 75
Node-XY-32b ::=  SEQUENCE {
   x  Offset-B16,
   y  Offset-B16
   }
 
 
 
-- DF_ObstacleDetection (Desc Name) Record 76
ObstacleDetection ::=  SEQUENCE {  
   obDist      ObstacleDistance,  -- Obstacle Distance        
   obDirect    Angle,             -- Obstacle Direction        
   dateTime    DDateTime,         -- time detected
   ...
   }
 
 
 
-- DF_OffsetSystem (Desc Name) Record 77
OffsetSystem ::=  CHOICE {
   xy  NodeListXY, -- offsets of 1.0 centimeters 
   ll  NodeListLL  -- offsets of 0.1 microdegrees
   }
 
 
 
-- DF_OverlayLaneList (Desc Name) Record 78
OverlayLaneList ::=  SEQUENCE (SIZE(1..5)) OF LaneID
   -- The unique ID numbers for any lane object which have
   -- spatial paths that overlay (run on top of, and not
   -- simply cross with) the current lane.
   -- Such as a train path that overlays a motor vehicle
   -- lane object for a roadway segment.
 
 
 
-- DF_PathHistory (Desc Name) Record 79
PathHistory ::=  SEQUENCE {
   initialPosition  FullPositionVector    OPTIONAL,
   currGNSSstatus   GNSSstatus            OPTIONAL,   
   crumbData  	    PathHistoryPointList,
   ...
   }
 
 
 
-- DF_PathHistoryPoint (Desc Name) Record 80
PathHistoryPoint ::=  SEQUENCE {
   latOffset       OffsetLL-B18,
   lonOffset       OffsetLL-B18,
   elevationOffset VertOffset-B12,  
                   -- LLH position offset from last point
   timeOffset      TimeOffset,
                   -- Offset backwards in time 
   speed           Speed                 OPTIONAL, 
                   -- Speed over the reported period
   posAccuracy     PositionalAccuracy    OPTIONAL, 
                   -- The accuracy of this value
   heading         CoarseHeading         OPTIONAL, 
                   -- overall heading 
   ...
   }
 
 
 
-- DF_PathHistoryPointList (Desc Name) Record 81
PathHistoryPointList ::=  SEQUENCE (SIZE(1..23)) OF PathHistoryPoint
 
 
 
-- DF_PathPrediction (Desc Name) Record 82
PathPrediction ::=  SEQUENCE {
   radiusOfCurve RadiusOfCurvature, 
                 -- LSB units of 10cm
                 -- straight path to use value of 32767
   confidence    Confidence, 
                 -- LSB units of 0.5 percent
   ...  
   }
 
 
 
-- DF_PivotPointDescription (Desc Name) Record 83
PivotPointDescription ::=  SEQUENCE {
   pivotOffset  Offset-B11,   
                -- This gives a +- 10m range from the edge of the outline
                -- measured from the edge of the length of this unit
                -- a negative value is offset to inside the units
                -- a positive value is offset beyond the unit
   pivotAngle   Angle,
                -- Measured between the center-line of this unit 
                -- and the unit ahead which is pulling it.
                -- This value is required to project the units relative position
   pivots       PivotingAllowed,
                -- true if this unit can rotate about the pivot connection point
   ...
   }
 
 
 
-- DF_Position3D (Desc Name) Record 84
Position3D ::=  SEQUENCE {
   lat        Latitude,                -- in 1/10th micro degrees
   long       Longitude,               -- in 1/10th micro degrees
   elevation  Elevation  OPTIONAL,     -- in 10 cm units
   regional   RegionalExtension {{REGION.Reg-Position3D}} OPTIONAL,
   ...
   }
 
 
 
-- DF_PositionalAccuracy (Desc Name) Record 85
PositionalAccuracy ::=  SEQUENCE {
   -- NMEA-183 values expressed in strict ASN form
   semiMajor     SemiMajorAxisAccuracy,
   semiMinor     SemiMinorAxisAccuracy,
   orientation   SemiMajorAxisOrientation
}
 
 
 
-- DF_PositionConfidenceSet (Desc Name) Record 86
PositionConfidenceSet ::=  SEQUENCE {
   pos        PositionConfidence, -- for both horizontal directions
   elevation  ElevationConfidence 
   }
 
 
 
-- DF_PreemptPriorityList (Desc Name) Record 87
PreemptPriorityList ::=  SEQUENCE (SIZE(1..32)) OF SignalControlZone

SignalControlZone ::=  SEQUENCE {
  zone  RegionalExtension {{REGION.Reg-SignalControlZone}},
  ...
  }
 
 
 
-- DF_PrivilegedEvents (Desc Name) Record 88
PrivilegedEvents ::=  SEQUENCE {
   -- CERT SSP Privilege Details
   sspRights   SSPindex, -- index = TBD
   -- The active event list
   event  PrivilegedEventFlags,
   ...
}
 
 
 
-- DF_RegionList (Desc Name) Record 89
RegionList ::=  SEQUENCE (SIZE(1..64)) OF RegionOffsets
   -- the Position3D ref point (starting point or anchor)
   -- is found in the outer object.
 
 
 
-- DF_RegionOffsets (Desc Name) Record 90
RegionOffsets ::=  SEQUENCE {
   xOffset  OffsetLL-B16,  -- was: INTEGER (-32767..32767), 
   yOffset  OffsetLL-B16,
   zOffset  OffsetLL-B16 OPTIONAL
            -- all in signed values where 
            -- the LSB is in units of 1 meter  
   }
 
 
 
-- DF_RegionPointSet (Desc Name) Record 91
RegionPointSet ::=  SEQUENCE {
   anchor           Position3D  OPTIONAL, 
   scale            Zoom OPTIONAL, 
   nodeList         RegionList,      
                    -- path details of the regions outline        
   ...             
   }
 
 
 
-- DF_RegulatorySpeedLimit (Desc Name) Record 92
RegulatorySpeedLimit ::=  SEQUENCE {
   type        SpeedLimitType, 
               -- The type of regulatory speed which follows
   speed       Velocity
               -- The speed in units of 0.02 m/s
               -- See Section 11 for converting and tranlating 
               -- speed expressed in MPH into units of m/s
   }
 
 
 
-- DF_RequestedItem (Desc Name) Record 93
RequestedItemList ::=  SEQUENCE (SIZE(1..32)) OF  RequestedItem
 
 
 
-- DF_RequestorDescription (Desc Name) Record 94
RequestorDescription ::=  SEQUENCE {
   id                VehicleID, 
                     -- The BSM or CAM ID of the requestor
                     -- This ID is presumed not to change 
                     -- during the exchange
   type              RequestorType OPTIONAL,
                     -- Information regarding all type and class data
                     -- about the requesting vehicle 
   position          RequestorPositionVector OPTIONAL,
                     -- The location of the requesting vehicle
   name              DescriptiveName OPTIONAL,
                     -- A human readable name for debugging use
   -- Support for Transit requests
   routeName         DescriptiveName OPTIONAL,
                     -- A string for transit operations use
   transitStatus     TransitVehicleStatus OPTIONAL,
                     -- current vehicle state (loading, etc.)
   transitOccupancy  TransitVehicleOccupancy OPTIONAL,
                     -- current vehicle occupancy 
   transitSchedule   DeltaTime OPTIONAL, 
                     -- current vehicle schedule adherence 

   regional          RegionalExtension {{REGION.Reg-RequestorDescription}} OPTIONAL,
   ...
   }
 
 
 
-- DF_RequestorPositionVector (Desc Name) Record 95
RequestorPositionVector ::=  SEQUENCE {
   position           Position3D,
   heading            Angle OPTIONAL, 
   speed              TransmissionAndSpeed OPTIONAL,
   ...  
   }
 
 
 
-- DF_RequestorType (Desc Name) Record 96
RequestorType ::=  SEQUENCE {
   -- Defines who is requesting
   role         BasicVehicleRole, -- Basic role of this user at this time
   subrole      RequestSubRole OPTIONAL, -- A local list with role based items 
    
   -- Defines what kind of request (a level of importance in the Priority Scheme)
   request      RequestImportanceLevel OPTIONAL, -- A local list with request items 
   
   -- Additional classification details 
   iso3883      Iso3833VehicleType OPTIONAL,
   hpmsType     VehicleType OPTIONAL,  -- HPMS classification types

   regional     RegionalExtension {{REGION.Reg-RequestorType}} OPTIONAL,
   ...
   }
 
 
 
-- DF_RestrictionClassAssignment (Desc Name) Record 97
RestrictionClassAssignment ::=  SEQUENCE {
   id       RestrictionClassID,
            -- the unique value (within an intersection or local region)
            -- that is assigned to this group of users
   users    RestrictionUserTypeList 
            -- The list of user types/classes 
            -- to which this restriction ID applies
   }
 
 
 
-- DF_RestrictionClassList (Desc Name) Record 98
RestrictionClassList ::=  SEQUENCE (SIZE(1..254)) OF RestrictionClassAssignment
 
 
 
-- DF_RestrictionUserType (Desc Name) Record 99
RestrictionUserType ::=  CHOICE {
   basicType   RestrictionAppliesTo,
               -- a set of the most commonly used types
   regional    RegionalExtension {{REGION.Reg-RestrictionUserType}}, 
   ...
   }
 
 
 
-- DF_RestrictionUserTypeList (Desc Name) Record 100
RestrictionUserTypeList ::=  SEQUENCE (SIZE(1..16)) OF  RestrictionUserType
 
 
 
-- DF_RoadLaneSetList (Desc Name) Record 101
RoadLaneSetList ::=  SEQUENCE (SIZE(1..255)) OF GenericLane
 
 
 
-- DF_RoadSegment (Desc Name) Record 102
RoadSegment ::=  SEQUENCE {
   name        DescriptiveName OPTIONAL,
   id          RoadSegmentReferenceID,
                           -- a globally unique value for the segment
   revision    MsgCount,    
   -- Required default values about the descriptions to follow
   refPoint    Position3D, -- the reference from which subsequent
                           -- data points are offset until a new
                           -- point is used.
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given   
                            -- See Section 11 for converting and  
                            -- tranlating speed expressed in MPH 
                            -- into units of m/s
                         
   -- Data describing disruptions in the RoadSegment
   -- such as work zones etc will be added here;
   -- in the US the SAE ITIS codes would be used here
   -- The details regarding each lane type in the RoadSegment
   roadLaneSet RoadLaneSetList,   
  
   regional    RegionalExtension {{REGION.Reg-RoadSegment}} OPTIONAL,
   ...
   }
 
 
 
-- DF_RoadSegmentList (Desc Name) Record 103
RoadSegmentList ::=  SEQUENCE (SIZE(1..32)) OF RoadSegment
 
 
 
-- DF_RoadSegmentReferenceID (Desc Name) Record 104
RoadSegmentReferenceID ::=  SEQUENCE {
   region  RoadRegulatorID OPTIONAL,
           -- a globally unique regional assignment value
           -- typical assigned to a regional DOT authority
           -- the value zero shall be used for testing needs
   id      RoadSegmentID
           -- a unique mapping to the road segment
           -- in question within the above region of use
           -- during its period of aggiment and use
           -- note that unlike intserectionID values, 
           -- this value can be reused by the region
   }
 
 
 
-- DF_RoadSignID (Desc Name) Record 105
RoadSignID ::=  SEQUENCE {
   position        Position3D,
                   -- Location of sign
   viewAngle       HeadingSlice,
                   -- Vehicle direction of travel while
                   -- facing active side of sign
   mutcdCode       MUTCDCode OPTIONAL,
                   -- Tag for MUTCD code or "generic sign" 
   crc             MsgCRC OPTIONAL 
                   -- Used to provide a check sum
   }
 
 
 
-- DF_RTCMheader (Desc Name) Record 106
RTCMheader ::=  SEQUENCE {
   status     GNSSstatus,
   offsetSet  AntennaOffsetSet
   }
 
 
 
-- DF_RTCMmessageList (Desc Name) Record 107
RTCMmessageList ::=  SEQUENCE (SIZE(1..5)) OF RTCMmessage
 
 
 
-- DF_RTCMPackage (Desc Name) Record 108
RTCMPackage ::=  SEQUENCE {  
   -- precise ant position and noise data for a rover
   rtcmHeader  RTCMheader OPTIONAL,  
                    
   -- one or more RTCM messages
   msgs        RTCMmessageList,
   ...  
   }
 
 
 
-- DF_Sample (Desc Name) Record 109
Sample ::=  SEQUENCE {
   sampleStart  INTEGER(0..255),   --  Sample Starting Point
   sampleEnd    INTEGER(0..255)    --  Sample Ending Point
   }
 
 
 
-- DF_SegmentAttributeLLList (Desc Name) Record 110
SegmentAttributeLLList ::=  SEQUENCE (SIZE(1..8)) OF SegmentAttributeLL
 
 
 
-- DF_SegmentAttributeXYList (Desc Name) Record 111
SegmentAttributeXYList ::=  SEQUENCE (SIZE(1..8)) OF SegmentAttributeXY
 
 
 
-- DF_ShapePointSet (Desc Name) Record 112
ShapePointSet ::=  SEQUENCE {
   anchor           Position3D     OPTIONAL, 
   laneWidth        LaneWidth      OPTIONAL, 
   directionality   DirectionOfUse OPTIONAL, 
   nodeList         NodeListXY,    -- XY path details of the lane and width           
   ...             
   }
 
 
 
-- DF_SignalRequest (Desc Name) Record 113
SignalRequest ::=  SEQUENCE {
   -- the unique ID of the target intersection 
   id            IntersectionReferenceID,  
   
   -- The unique requestID used by the requestor
   requestID     RequestID, 
  
   -- The type of request or cancel for priority or preempt use
   -- when a prior request is canceled, only the requestID is needed
   requestType   PriorityRequestType,   
   
   -- In typical use either an approach or a lane number would
   -- be given, this indicates the requested 
   -- path through the intersection to the degree it is known.
   inBoundLane   IntersectionAccessPoint,       
                 --  desired entry approach or lane
   outBoundLane  IntersectionAccessPoint OPTIONAL,       
                 --  desired exist approach or lane
                 -- the values zero is used to indicate 
                 -- intent to stop within the intersection
   regional      RegionalExtension {{REGION.Reg-SignalRequest}} OPTIONAL,
   ...
   }
 
 
 
-- DF_SignalRequesterInfo (Desc Name) Record 114
SignalRequesterInfo ::=  SEQUENCE {
   -- These three items serve to uniquely identify the requester
   -- and the specific request to all parties
   id             VehicleID,
   request        RequestID,
   sequenceNumber MsgCount,
   role           BasicVehicleRole OPTIONAL,

   typeData       RequestorType OPTIONAL, 
                  -- Used when addition data besides the role
                  -- is needed, at which point the role entry
                  -- above is not sent.
   ...
   }
 
 
 
-- DF_SignalRequestList (Desc Name) Record 115
SignalRequestList ::=  SEQUENCE (SIZE(1..32)) OF SignalRequestPackage
 
 
 
-- DF_SignalRequestPackage (Desc Name) Record 116
SignalRequestPackage ::=  SEQUENCE {
   request        SignalRequest,
                  -- The specific request to the intersection
                  -- contains IntersectionID, request type,
                  -- requested action (approach/lane request)

   -- The Estimated Time of Arrival (ETA) when the service is requested
   minute         MinuteOfTheYear OPTIONAL,
   second         DSecond OPTIONAL,
   duration       DSecond OPTIONAL,
                  -- The duration value is used to provide a short interval that
                  -- extends the ETA so that the requesting vehicle can arrive at 
                  -- the point of service with uncertainty or with some desired
                  -- duration of service. This concept can be used to avoid needing 
                  -- to frequently update the request.
                  -- The requester must update the ETA and duration values if the
                  -- period of services extends beyond the duration time.  
                  -- It should be assumed that if the vehicle does not clear the
                  -- intersection when the duration is reached, the request will 
                  -- be cancelled and the intersection will revert to 
                  -- normal operation.
   
   regional       RegionalExtension {{REGION.Reg-SignalRequestPackage}} OPTIONAL,
   ...  
   }
 
 
 
-- DF_SignalStatus (Desc Name) Record 117
SignalStatus ::=  SEQUENCE {
   sequenceNumber MsgCount,
                  -- changed whenever the below contents have change
   id             IntersectionReferenceID,
                  -- this provides a unique mapping to the 
                  -- intersection map in question
                  -- which provides complete location 
                  -- and approach/move/lane data
                  -- as well as zones for priority/preemption
   sigStatus      SignalStatusPackageList,
                  -- a list of detailed status containing all
                  -- priority or preemption state data, both
                  -- active and pending, and whom requested it
                  -- requests which are denied are also listed
                  -- here for a short period of time
   regional       RegionalExtension {{REGION.Reg-SignalStatus}} OPTIONAL,
   ...  
   }
 
 
 
-- DF_SignalStatusList (Desc Name) Record 118
SignalStatusList ::=  SEQUENCE (SIZE(1..32)) OF SignalStatus
 
 
 
-- DF_SignalStatusPackage (Desc Name) Record 119
SignalStatusPackage ::=  SEQUENCE {
   -- The party that made the initial SRM request
   requester    SignalRequesterInfo OPTIONAL,
   -- The lanes or approaches used in the request
   inboundOn    IntersectionAccessPoint, -- estimated lane / approach of vehicle
   outboundOn   IntersectionAccessPoint OPTIONAL,

   -- The Estimated Time of Arrival (ETA) when the service is requested
   -- This data echos the data of the request 
   minute       MinuteOfTheYear OPTIONAL,
   second       DSecond OPTIONAL,
      duration     DSecond OPTIONAL,

   -- the SRM status for this request
   status       PrioritizationResponseStatus,
                -- Status of request, this may include rejection

   regional     RegionalExtension {{REGION.Reg-SignalStatusPackage}} OPTIONAL,
   ...  
   }
 
 
 
-- DF_SignalStatusPackageList (Desc Name) Record 120
SignalStatusPackageList ::=  SEQUENCE (SIZE(1..32)) OF SignalStatusPackage
 
 
 
-- DF_Snapshot (Desc Name) Record 121
Snapshot ::=  SEQUENCE {
   thePosition  FullPositionVector,          
                -- data of the position and speed, 
   safetyExt    VehicleSafetyExtensions OPTIONAL, 
   datSet       VehicleStatus           OPTIONAL,  
                -- a seq of data frames
                -- which encodes the data
   ...  
   }
 
 
 
-- DF_SnapshotDistance (Desc Name) Record 122
SnapshotDistance ::=  SEQUENCE {
   distance1   GrossDistance,   -- meters
   speed1      GrossSpeed,      -- meters/second
   distance2   GrossDistance,   -- meters
   speed2      GrossSpeed       -- meters/second
   }
 
 
 
-- DF_SnapshotTime (Desc Name) Record 123
SnapshotTime ::=  SEQUENCE {
   speed1  GrossSpeed,     -- meters/sec - the instantaneous speed  
                           -- when the calculation is performed
   time1   SecondOfTime,   -- in seconds
   speed2  GrossSpeed,     -- meters/sec - the instantaneous speed 
                           -- when the calculation is performed
   time2   SecondOfTime    -- in seconds
   }
 
 
 
-- DF_SpecialVehicleExtensions (Desc Name) Record 124
SpecialVehicleExtensions ::=  SEQUENCE {
   -- The content below requires SSP permisisons to transmit

   -- The entire EVA message has be reduced to these two items
   vehicleAlerts  EmergencyDetails OPTIONAL,
   -- Description or Direction from an emergency vehicle
   description    EventDescription  OPTIONAL, -- short ITIS description
   
   -- Trailers for both passenger vehicles and heavy trucks
   trailers       TrailerData OPTIONAL,

   -- HAZMAT and Cargo details to be added

   -- Wideload, oversized load to be added

   ...
   }
 
 
 
-- DF_Speed_Heading_Throttle_Confidence (Desc Name) Record 125
SpeedandHeadingandThrottleConfidence ::=  SEQUENCE {
   heading   HeadingConfidence,    
   speed     SpeedConfidence,      
   throttle  ThrottleConfidence    
   }
 
 
 
-- DF_ITIS_Phrase_SpeedLimit (Desc Name) Record 126
SpeedLimit ::=  SEQUENCE (SIZE(1..16)) OF SEQUENCE {
  item CHOICE    {
       itis   ITIS.ITIScodes,
       text   ITIStextPhrase
       }  
  }
 
 
 
-- DF_SpeedLimitList (Desc Name) Record 127
SpeedLimitList ::=  SEQUENCE (SIZE(1..9)) OF RegulatorySpeedLimit
 
 
 
-- DF_SpeedProfile (Desc Name) Record 128
SpeedProfile ::=  SEQUENCE {
   -- Composed of set of measured average speeds
   speedReports SpeedProfileMeasurementList,  
   ...
   }
 
 
 
-- DF_SpeedProfileMeasurementList (Desc Name) Record 129
SpeedProfileMeasurementList ::=  SEQUENCE (SIZE(1..20)) OF SpeedProfileMeasurement
 
 
 
-- DF_SupplementalVehicleExtensions (Desc Name) Record 130
SupplementalVehicleExtensions ::=  SEQUENCE {
   -- Note that VehicleEventFlags, ExteriorLights, 
   -- PathHistory, and PathPrediction are in VehicleSafetyExtensions 

   -- Vehicle Type Classification Data
   classification   BasicVehicleClass        OPTIONAL,
   classDetails     VehicleClassification    OPTIONAL,
   vehicleData      VehicleData              OPTIONAL,

   -- Various V2V Probe Data
   weatherReport    WeatherReport            OPTIONAL, 
   weatherProbe     WeatherProbe             OPTIONAL, 

   -- Detected Obstacle data
   obstacle         ObstacleDetection        OPTIONAL,
   
   -- Oncoming lane speed reporting
   speedProfile     SpeedProfile             OPTIONAL, 

   -- Raw GNSS measurements
   theRTCM          RTCMPackage              OPTIONAL, 

   regional  RegionalExtension {{REGION.Reg-SupplementalVehicleExtensions}} OPTIONAL,
   ...
   }
 
 
 
-- DF_TimeChangeDetails (Desc Name) Record 131
TimeChangeDetails ::=  SEQUENCE {
   startTime   TimeMark           OPTIONAL,
               -- When this phase 1st started
   minEndTime  TimeMark,
               -- Expected shortest end time
   maxEndTime  TimeMark           OPTIONAL,
               -- Expected longer end time
   
   likelyTime  TimeMark           OPTIONAL,
               -- Best predicted value based on other data              
   confidence  TimeIntervalConfidence OPTIONAL,
               -- Applies to above time element only
   
   nextTime    TimeMark           OPTIONAL
               -- A rough estimate of time when 
               -- this phase may next occur again
               -- used to support various ECO driving power 
               -- management needs.
   }
 
 
 
-- DF_TrailerData (Desc Name) Record 132
TrailerData ::=  SEQUENCE {
   -- CERT SSP Privilege Details
   sspRights   SSPindex, -- index = TBD

   -- Offset connection point details from the 
   -- hauling vehicle to the first trailer unit
   connection  PivotPointDescription,

   -- One of more Trailer or Dolly Descriptions 
   -- (each called a unit)
   units       TrailerUnitDescriptionList,

   ...
}
 
 
 
-- DF_TrailerHistoryPoint (Desc Name) Record 133
TrailerHistoryPoint ::=  SEQUENCE {
   pivotAngle       Angle,
                    -- angle with respect to the lead unit
   timeOffset       TimeOffset,
                    -- offset backwards in time 
   -- Position relative to the hauling Vehicle
   positionOffset   Node-XY-24b, 
   elevationOffset  VertOffset-B07 OPTIONAL,   
   heading          CoarseHeading OPTIONAL, 
                    -- overall heading 
   ...
   }
 
 
 
-- DF_TrailerHistoryPointList (Desc Name) Record 134
TrailerHistoryPointList ::=  SEQUENCE (SIZE(1..23)) OF TrailerHistoryPoint
 
 
 
-- DF_TrailerUnitDescription (Desc Name) Record 135
TrailerUnitDescription ::=  SEQUENCE {
   isDolly          IsDolly, -- if false this is a trailer
   width            VehicleWidth,   
   length           VehicleLength,  
   height           VehicleHeight OPTIONAL,
   mass             TrailerMass   OPTIONAL,
   bumperHeights    BumperHeights OPTIONAL,
   centerOfGravity  VehicleHeight OPTIONAL,
   -- The front pivot point of the unit
   frontPivot       PivotPointDescription,
   -- The rear pivot point connecting to the next element, 
   -- if present and used (implies another unit is connected)
   rearPivot        PivotPointDescription OPTIONAL,

   -- Rear wheel pivot point center-line offset
   -- measured from the rear of the above length
   rearWheelOffset  Offset-B12 OPTIONAL,   
                    -- the effective center-line of the wheel set

   -- Current Position relative to the hauling Vehicle
   positionOffset   Node-XY-24b, 
   elevationOffset  VertOffset-B07 OPTIONAL,   
   -- we may want heading and velocity to be added here ???
   
   -- Past Position history relative to the hauling Vehicle
   crumbData  	    TrailerHistoryPointList OPTIONAL, 
   ...
   }
 
 
 
-- DF_TrailerUnitDescriptionList (Desc Name) Record 136
TrailerUnitDescriptionList ::=  SEQUENCE (SIZE(1..8)) OF TrailerUnitDescription
 
 
 
-- DF_TransmissionAndSpeed (Desc Name) Record 137
TransmissionAndSpeed ::=  SEQUENCE {
   transmisson   TransmissionState,
   speed         Velocity
   }
 
 
 
-- DF_TravelerDataFrame (Desc Name) Record 138
TravelerDataFrame ::=  SEQUENCE {
   -- Part I, Frame header
   sspTimRights    SSPindex,  
   frameType   TravelerInfoType,  -- (enum, advisory or road sign)
   msgId CHOICE {
         furtherInfoID   FurtherInfoID, -- links to ATIS msg
         roadSignID      RoadSignID     -- an ID to other data
         },
   startYear   DYear OPTIONAL,  -- only if needed
   startTime   MinuteOfTheYear,
   duratonTime MinutesDuration,
   priority    SignPrority,
  
   -- Part II, Applicable Regions of Use
   sspLocationRights  SSPindex,  
   regions SEQUENCE (SIZE(1..16)) OF GeographicalPath,

   -- Part III, Content
   sspMsgRights1    SSPindex,  -- allowed message types
   sspMsgRights2    SSPindex,  -- allowed message content
   content  CHOICE {
            advisory     ITIS.ITIScodesAndText,           
                         -- typical ITIS warnings
            workZone     WorkZone,       
                         -- work zone signs and directions
            genericSign  GenericSignage, 
                         -- MUTCD signs and directions
            speedLimit   SpeedLimit,     
                         -- speed limits and cautions
            exitService  ExitService     
                         -- roadside avaiable services
            -- other types may be added in future revisions
            },   
   url     URL-Short OPTIONAL,  -- May link to image or other content
   ...
   }
 
 
 
-- DF_TravelerDataFrameList (Desc Name) Record 139
TravelerDataFrameList ::=  SEQUENCE (SIZE(1..8)) OF TravelerDataFrame
 
 
 
-- DF_ValidRegion (Desc Name) Record 140
ValidRegion ::=  SEQUENCE {
   direction         HeadingSlice,
                     -- field of view over which this applies,
   extent            Extent OPTIONAL,  
                     -- the spatial distance over which this
                     -- message applies and should be presented 
                     -- to the driver
   area    CHOICE  {
      shapePointSet  ShapePointSet,
                     -- A short road segment
      circle         Circle,
                     -- A point and radius
      regionPointSet RegionPointSet 
                     -- Wide area enclosed regions
      }
   }
 
 
 
-- DF_VehicleClassification (Desc Name) Record 141
VehicleClassification ::=  SEQUENCE {
   -- Composed of the following elements:

   -- The 'master' DSRC list used when space is liited
   keyType         BasicVehicleClass OPTIONAL,

   -- Types used in the MAP/SPAT/SSR/SRM exchanges 
   role            BasicVehicleRole OPTIONAL, -- Basic CERT role at a given time
   iso3883         Iso3833VehicleType OPTIONAL,
   hpmsType        VehicleType OPTIONAL,  -- HPMS classification types
   
   -- ITIS types for classes of vehicle and agency
   vehicleType     ITIS.VehicleGroupAffected OPTIONAL,      
   responseEquip   ITIS.IncidentResponseEquipment OPTIONAL, 
   responderType   ITIS.ResponderGroupAffected OPTIONAL,    

   regional        RegionalExtension {{REGION.Reg-VehicleClassification}} OPTIONAL,
   ...
   }
 
 
 
-- DF_VehicleData (Desc Name) Record 142
VehicleData ::=  SEQUENCE {    
   -- Values for width and length are sent in BSM part I 
   height        VehicleHeight   OPTIONAL,
   bumpers       BumperHeights   OPTIONAL,
   mass          VehicleMass     OPTIONAL,
   trailerWeight TrailerWeight   OPTIONAL,
   ...
   }
 
 
 
-- DF_VehicleID (Desc Name) Record 143
VehicleID ::=  CHOICE {
   entityID     TemporaryID,
   stationID    StationID
   }
 
 
 
-- DF_VehicleIdent (Desc Name) Record 144
VehicleIdent ::=  SEQUENCE {
   name           DescriptiveName OPTIONAL,
                  -- a human readable name for debugging use
   vin            VINstring OPTIONAL,
                  -- vehicle VIN value
   ownerCode      IA5String(SIZE(1..32)) OPTIONAL,
                  -- vehicle owner code 
   id             VehicleID OPTIONAL, 
                  -- same value used in the BSM
      
   vehicleType    VehicleType  OPTIONAL, 
   vehicleClass   CHOICE {
                     vGroup   ITIS.VehicleGroupAffected,
                     rGroup   ITIS.ResponderGroupAffected,
                     rEquip   ITIS.IncidentResponseEquipment  
                  } OPTIONAL, 
   ...  
   }
 
 
 
-- DF_VehicleSafetyExtensions (Desc Name) Record 145
VehicleSafetyExtensions ::=  SEQUENCE {
   events             VehicleEventFlags OPTIONAL,
   pathHistory        PathHistory       OPTIONAL, 
   pathPrediction     PathPrediction    OPTIONAL,
   lights             ExteriorLights    OPTIONAL,                       
   ...
   }
 
 
 
-- DF_VehicleSize (Desc Name) Record 146
VehicleSize ::=  SEQUENCE {
   width     VehicleWidth,
   length    VehicleLength
   }
 
 
 
-- DF_VehicleStatus (Desc Name) Record 147
VehicleStatus ::=  SEQUENCE { 
   lights          ExteriorLights OPTIONAL,                 -- Exterior Lights
   lightBar        LightbarInUse  OPTIONAL,                 -- PS Lights
   
   wipers          WiperSet OPTIONAL,                      -- Wipers
   
   brakeStatus     BrakeSystemStatus OPTIONAL, 
                                                            -- Braking Data
   brakePressure   BrakeAppliedPressure  OPTIONAL,          -- Braking Pressure
   roadFriction    CoefficientOfFriction OPTIONAL,          -- Roadway Friction 
   
      
   sunData         SunSensor             OPTIONAL,          -- Sun Sensor        
   rainData        RainSensor            OPTIONAL,          -- Rain Sensor        
   airTemp         AmbientAirTemperature OPTIONAL,          -- Air Temperature    
   airPres         AmbientAirPressure    OPTIONAL,          -- Air Pressure
   
   steering   SEQUENCE {
         angle      SteeringWheelAngle,   
         confidence SteeringWheelAngleConfidence   OPTIONAL,    
         rate       SteeringWheelAngleRateOfChange OPTIONAL,   
         wheels     DrivingWheelAngle              OPTIONAL
         } OPTIONAL,                                        -- steering data
   
   accelSets  SEQUENCE {
         accel4way       AccelerationSet4Way           OPTIONAL, 
         vertAccelThres  VerticalAccelerationThreshold OPTIONAL, 
                                                       -- Wheel Exceeded point
         yawRateCon      YawRateConfidence             OPTIONAL, 
                                                        -- Yaw Rate Confidence
         hozAccelCon     AccelerationConfidence        OPTIONAL,     
                                                        -- Acceleration Confidence 
         confidenceSet   ConfidenceSet                 OPTIONAL
                                                       -- general ConfidenceSet 
         } OPTIONAL, 
                                  
   
   object     SEQUENCE {
         obDist          ObstacleDistance,          -- Obstacle Distance        
         obDirect        Angle,                     -- Obstacle Direction        
         dateTime        DDateTime                  -- time detected
         } OPTIONAL,                                -- detected Obstacle data
   
   
   
   fullPos         FullPositionVector OPTIONAL,     -- complete set of time and
                                                    -- position, speed, heading
   throttlePos     ThrottlePosition OPTIONAL,
   speedHeadC      SpeedandHeadingandThrottleConfidence OPTIONAL,    
   speedC          SpeedConfidence OPTIONAL,
   
   vehicleData   SEQUENCE {    
         height        VehicleHeight,
         bumpers       BumperHeights,
         mass          VehicleMass,
         trailerWeight TrailerWeight,
         type          VehicleType 
         -- values for width and length are sent in BSM part I as well. 
         } OPTIONAL,                                        -- vehicle data
   
   vehicleIdent   VehicleIdent OPTIONAL,                    -- comm vehicle data
 
   j1939data      J1939data OPTIONAL,           -- Various SAE J1938 data items
     
   weatherReport SEQUENCE {    
         isRaining        NTCIP.EssPrecipYesNo,
         rainRate         NTCIP.EssPrecipRate       OPTIONAL,
         precipSituation  NTCIP.EssPrecipSituation  OPTIONAL,
         solarRadiation   NTCIP.EssSolarRadiation   OPTIONAL,
         friction         NTCIP.EssMobileFriction   OPTIONAL
         } OPTIONAL,                                        -- local weather data
      
   gnssStatus      GNSSstatus          OPTIONAL,              -- vehicle's GPS
 
   ...          
   }
 
 
 
-- DF_VehicleStatusRequest (Desc Name) Record 148
VehicleStatusRequest ::=  SEQUENCE {
   dataType             VehicleStatusDeviceTypeTag, 
   subType              INTEGER (1..15)   OPTIONAL, 
   sendOnLessThenValue  INTEGER (-32767..32767) OPTIONAL, 
   sendOnMoreThenValue  INTEGER (-32767..32767) OPTIONAL, 
   sendAll              BOOLEAN OPTIONAL, 
   ... 
   }
 
 
 
-- DF_VehicleStatusRequest (Desc Name) Record 149
VehicleStatusRequestList ::=  SEQUENCE (SIZE(1..32)) OF VehicleStatusRequest
 
 
 
-- DF_VerticalOffset (Desc Name) Record 150
VerticalOffset ::=  CHOICE {
   -- Vertical Offset
   -- All below in steps of 10cm above or below the reference ellipsoid
   offset1         VertOffset-B07,  -- with a range of +-   6.3 meters vertical
   offset2         VertOffset-B08,  -- with a range of +-  12.7 meters vertical
   offset3         VertOffset-B09,  -- with a range of +-  25.5 meters vertical
   offset4         VertOffset-B10,  -- with a range of +-  51.1 meters vertical
   offset5         VertOffset-B11,  -- with a range of +- 102.3 meters vertical
   offset6         VertOffset-B12,  -- with a range of +- 204.7 meters vertical
   elevation       Elevation,       -- with a range of -409.5 to + 6143.9 meters
   regional        RegionalExtension {{REGION.Reg-VerticalOffset}}  
                                    -- offset which follows is of a
                                    -- regional definition type
   }
 
 
 
-- DF_WeatherProbe (Desc Name) Record 151
WeatherProbe ::=  SEQUENCE {
   airTemp      AmbientAirTemperature  OPTIONAL,
   airPressure  AmbientAirPressure     OPTIONAL,
   rainRates    WiperSet               OPTIONAL,
   ...
   }
 
 
 
-- DF_WeatherReport (Desc Name) Record 152
WeatherReport ::=  SEQUENCE {    
   isRaining        NTCIP.EssPrecipYesNo,
   rainRate         NTCIP.EssPrecipRate       OPTIONAL,
   precipSituation  NTCIP.EssPrecipSituation  OPTIONAL,
   solarRadiation   NTCIP.EssSolarRadiation   OPTIONAL,
   friction         NTCIP.EssMobileFriction   OPTIONAL,
   roadFriction     CoefficientOfFriction     OPTIONAL,   
   ... 
   }
 
 
 
-- DF_WiperSet (Desc Name) Record 153
WiperSet ::=  SEQUENCE {
   statusFront    WiperStatus,
   rateFront      WiperRate,
   statusRear     WiperStatus      OPTIONAL,
   rateRear       WiperRate        OPTIONAL
   }
 
 
 
-- DF_ITIS_Phrase_WorkZone (Desc Name) Record 154
WorkZone ::=  SEQUENCE (SIZE(1..16)) OF SEQUENCE {
  item CHOICE    {
       itis   ITIS.ITIScodes,
       text   ITIStextPhrase
       }  
  }
 
 
-- -_-_-_-_-_-_-_-_-_-_-_-_-_-_-_-_-_-_-_-_-_-_-_-_-_-_-_-_
-- 
-- Start of entries from table Data_Elements...
-- This table typicaly contains data element entries.
-- -_-_-_-_-_-_-_-_-_-_-_-_-_-_-_-_-_-_-_-_-_-_-_-_-_-_-_-_
-- 
 
 
-- DE_Acceleration (Desc Name) Record 1
Acceleration ::= INTEGER (-2000..2001) 
   -- LSB units are 0.01 m/s^2
   -- the value 2000 shall be used for values greater than 2000     
   -- the value -2000 shall be used for values less than -2000  
   -- a value of 2001 shall be used for Unavailable
 
 
 
-- DE_AccelerationConfidence (Desc Name) Record 2
AccelerationConfidence ::= ENUMERATED {
   unavailable  (0), -- Not Equipped or data is unavailable
   accl-100-00  (1), -- 100  meters / second squared
   accl-010-00  (2), -- 10   meters / second squared
   accl-005-00  (3), -- 5    meters / second squared
   accl-001-00  (4), -- 1    meters / second squared
   accl-000-10  (5), -- 0.1  meters / second squared
   accl-000-05  (6), -- 0.05 meters / second squared
   accl-000-01  (7)  -- 0.01 meters / second squared
   } -- Encoded as a 3 bit value
 
 
 
-- DE_AdvisorySpeedType (Desc Name) Record 3
AdvisorySpeedType ::= ENUMERATED {
    none       (0),
    greenwave  (1),
    ecoDrive   (2),
    transit    (4),
    ...  
    } -- Note: subject to further growth
 
 
 
-- DE_AgeGroup (Desc Name) Record 4
AgeGroup ::= ENUMERATED { 
   unavailable                     (0),
   infants-Toddlers                (1), -- ages 0-2 
   earlyChildhood                  (2), -- ages 3-7
   lateChildhood-EarlyAdolescense  (3), -- ages 8-15
   lateAdolescence-EarlyAdulthood  (4), -- ages 16 or greater
   adult                           (5), --  
   seniorAdult                     (6), -- those who move a bit slowly
   ...
   }
 
 
 
-- DE_AllowedManeuvers (Desc Name) Record 5
AllowedManeuvers ::= BIT STRING {
    -- With bits as defined:
    -- Allowed and maneuvers at path end (stop line)
    -- All maneuvers with bits not set are therefore prohibited !
    -- A value of zero shall be used for unknown, indicating no Maneuver
    maneuverStraightAllowed      (0), 
                                  -- a Straight movement is allowed in this lane
    maneuverLeftAllowed          (1),  
                                 -- a Left Turn movement is allowed in this lane
    maneuverRightAllowed         (2), 
                                 -- a Right Turn movement is allowed in this lane
    maneuverUTurnAllowed         (3), 
                                 -- a U turn movement is allowed in this lane
    maneuverLeftTurnOnRedAllowed (4), 
                                 -- a Stop, and then proceed when safe movement 
                                 -- is allowed in this lane  
    maneuverRightTurnOnRedAllowed (5), 
                                 -- a Stop, and then proceed when safe movement 
                                 -- is allowed in this lane  
    maneuverLaneChangeAllowed    (6), 
                                 -- a movement which changes to an outer lane 
                                 -- on the egress side is allowed in this lane
                                 -- (example: left into either outbound lane)
    maneuverNoStoppingAllowed    (7), 
                                 -- the vehicle should not stop at the stop line
                                 -- (example: a flashing green arrow)
    yieldAllwaysRequired         (8), 
                                 -- the allowed movements above are not protected 
                                 -- (example: an permanent yellow condition)
    goWithHalt                   (9), 
                                 -- after making a full stop, may proceed
    caution                      (10), 
                                 -- proceed past stop line with caution
    reserved1                    (11)
                                 -- used to align to 12 Bit Field
   
   } (SIZE(12))
 
 
 
-- DE_AmbientAirPressure (Barometric Pressure) (Desc Name) Record 6
AmbientAirPressure ::= INTEGER (0..255) 
   -- 8 Bits in hPa starting at 580 with a resolution of 
   -- 2 hPa resulting in a range of 580 to 1090
 
 
 
-- DE_AmbientAirTemperature (Desc Name) Record 7
AmbientAirTemperature ::= INTEGER (0..191) -- in deg C with a -40 offset
 
 
 
-- DE_Angle (Desc Name) Record 8
Angle ::= INTEGER (0..28800) 
   -- LSB of 0.0125 degrees
   -- A range of 0 to 359.9875 degrees
 
 
 
-- DE_AnimalType (Desc Name) Record 9
AnimalType ::= ENUMERATED { 
   unavailable    (0), 
   serviceUse     (1),  -- Includes guide or police animals
   pet            (2),
   farm           (3),
   wild           (4),
   ...
   }
 
 
 
-- DE_AntiLockBrakeStatus (Desc Name) Record 10
AntiLockBrakeStatus ::= ENUMERATED {
   unavailable (0), -- B'00  Vehicle Not Equipped with ABS Brakes 
                    --       or ABS Brakes status is unavailable
   off         (1), -- B'01  Vehicle's ABS are Off
   on          (2), -- B'10  Vehicle's ABS are On ( but not Engaged )
   engaged     (3)  -- B'11  Vehicle's ABS control is Engaged 
   }
 
 
 
-- DE_ApproachID (Desc Name) Record 11
ApproachID ::= INTEGER (0..15) -- zero to be used when valid value is unknown
 
 
 
-- DE_Attachment (Desc Name) Record 12
Attachment ::= ENUMERATED { 
   unavailable                  (0),
   stroller                     (1),
   bicycleTrailer               (2),
   cart                         (3),
   wheelchair                   (4),
   otherWalkAssistAttachments   (5),
   pet                          (6),
   ...
   }
 
 
 
-- DE_AttachmentRadius (Desc Name) Record 13
AttachmentRadius ::= INTEGER (0..200) -- In LSB units of one decimeter
 
 
 
-- DE_AuxiliaryBrakeStatus (Desc Name) Record 14
AuxiliaryBrakeStatus ::= ENUMERATED {
   unavailable (0), -- B'00  Vehicle Not Equipped with Aux Brakes 
                    --       or Aux Brakes status is unavailable
   off         (1), -- B'01  Vehicle's Aux Brakes are Off
   on          (2), -- B'10  Vehicle's Aux Brakes are On ( Engaged )
   reserved    (3)  -- B'11 
   }
 
 
 
-- DE_J1939-71-Axle Location (Desc Name) Record 15
AxleLocation ::= INTEGER (0..127)
 
 
 
-- DE_J1939-71-Axle Weight (Desc Name) Record 16
AxleWeight ::= INTEGER (0..65535)
 
 
 
-- DE_BasicVehicleClass (Desc Name) Record 17
BasicVehicleClass ::= INTEGER (0..255)
unknownVehicleClass             BasicVehicleClass ::=  0  
                                -- Not Equipped, Not known or unavailable
specialVehicleClass             BasicVehicleClass ::=  1  
                                -- Special use    
--
--  Basic Passenger Motor Vehicle Types 
-- 
passenger-Vehicle-TypeUnknown   BasicVehicleClass ::=  10 -- default type
passenger-Vehicle-TypeOther     BasicVehicleClass ::=  11 
passenger-Vehicle-Gasoline      BasicVehicleClass ::=  12 -- Gasoline Powered
passenger-Vehicle-Electric      BasicVehicleClass ::=  13  
passenger-Vehicle-Hybrid        BasicVehicleClass ::=  14  
passenger-Vehicle-FuelCell      BasicVehicleClass ::=  15  
passenger-Vehicle-Gas           BasicVehicleClass ::=  16 -- Natural, propane, etc. 

--
-- Light Trucks, Pickup, Van, Panel
-- 
lightTruck-Vehicle-TypeUnknown  BasicVehicleClass ::=  20 -- default type
lightTruck-Vehicle-TypeOther    BasicVehicleClass ::=  21 

--
-- Trucks, Various axle types, includes HPMS items 
-- 
truck-Vehicle-TypeUnknown BasicVehicleClass ::=  25 -- default type
truck-Vehicle-TypeOther BasicVehicleClass ::=  26 
truck-axleCnt2  BasicVehicleClass ::=  27 -- Two axle, six tire single units    
truck-axleCnt3  BasicVehicleClass ::=  28 -- Three axle, single units    
truck-axleCnt4  BasicVehicleClass ::=  29 -- Four or more axle, single unit    
truck-axleCnt4Trailer BasicVehicleClass ::=  30 -- Four or less axle, single trailer    
truck-axleCnt5Trailer BasicVehicleClass ::=  31 -- Five or less axle, single trailer    
truck-axleCnt6Trailer BasicVehicleClass ::=  32 -- Six or more axle, single trailer    
truck-axleCnt5MultiTrailer BasicVehicleClass ::=  33 -- Five or less axle, multi-trailer    
truck-axleCnt6MultiTrailer BasicVehicleClass ::=  34 -- Six axle, multi-trailer    
truck-axleCnt7MultiTrailer BasicVehicleClass ::=  35 -- Seven or more axle, multi-trailer    

--
-- Motorcycle Types
--
motorcycle-TypeUnknown          BasicVehicleClass ::=  40 -- default type
motorcycle-TypeOther            BasicVehicleClass ::=  41
motorcycle-Cruiser-Standard     BasicVehicleClass ::=  42
motorcycle-SportUnclad          BasicVehicleClass ::=  43
motorcycle-SportTouring         BasicVehicleClass ::=  44
motorcycle-SupperSport          BasicVehicleClass ::=  45
motorcycle-Touring              BasicVehicleClass ::=  46
motorcycle-Trike                BasicVehicleClass ::=  47 

--
-- Transit Types
--
transit-TypeUnknown             BasicVehicleClass ::=  50 -- default type
transit-TypeOther               BasicVehicleClass ::=  51
transit-BRT                     BasicVehicleClass ::=  52
transit-ExpressBus              BasicVehicleClass ::=  53
transit-LocalBus                BasicVehicleClass ::=  54
transit-SchoolBus               BasicVehicleClass ::=  55
transit-FixedGuideway           BasicVehicleClass ::=  56
transit-Paratransit             BasicVehicleClass ::=  57
transit-Paratransit-Ambulance   BasicVehicleClass ::=  58

--
-- Emergency Vehicle Types
--
emergency-TypeUnknown            BasicVehicleClass ::=  60 -- default type
emergency-TypeOther              BasicVehicleClass ::=  61 -- includes federal users
emergency-Fire-Light-Vehicle     BasicVehicleClass ::=  62
emergency-Fire-Heavy-Vehicle     BasicVehicleClass ::=  63
emergency-Fire-Paramedic-Vehicle BasicVehicleClass ::=  64
emergency-Fire-Ambulance-Vehicle BasicVehicleClass ::=  65
emergency-Police-Light-Vehicle   BasicVehicleClass ::=  66
emergency-Police-Heavy-Vehicle   BasicVehicleClass ::=  67
emergency-Other-Responder        BasicVehicleClass ::=  68
emergency-Other-Ambulance        BasicVehicleClass ::=  69

--
-- Other DSRC Equipped Travelers
--
otherTraveler-TypeUnknown          BasicVehicleClass ::=  80 -- default type
otherTraveler-TypeOther            BasicVehicleClass ::=  81
otherTraveler-Pedestrian           BasicVehicleClass ::=  82
otherTraveler-Visually-Disabled    BasicVehicleClass ::=  83
otherTraveler-Physically-Disabled  BasicVehicleClass ::=  84
otherTraveler-Bicycle              BasicVehicleClass ::=  85
otherTraveler-Vulnerable-Roadworker BasicVehicleClass ::=  86

--
-- Other DSRC Equipped Device Types
--
infrastructure-TypeUnknown      BasicVehicleClass ::=  90 -- default type
infrastructure-Fixed            BasicVehicleClass ::=  91
infrastructure-Movable          BasicVehicleClass ::=  92
equipped-CargoTrailer           BasicVehicleClass ::=  93
 
 
 
-- DE_BasicVehicleRole (Desc Name) Record 18
BasicVehicleRole ::= ENUMERATED {
    -- Values used in the EU and in the US
    basicVehicle     (0), -- Light duty passenger vehicle type
    publicTransport  (1), -- Used in EU for Transit us
    specialTransport (2), -- Used in EU (e.g. heavy load)
    dangerousGoods   (3), -- Used in EU for any HAZMAT
    roadWork         (4), -- Used in EU for State and Local DOT uses
    roadRescue       (5), -- Used in EU and in the US to include tow trucks.
    emergency        (6), -- Used in EU for Police, Fire and Ambulance units
    safetyCar        (7), -- Used in EU for Escort vehicles
    -- Begin US unique numbering
    none-unknown    (10), -- added to follow current SAE style guidelines
    truck           (11), -- Heavy trucks with additional BSM rights and obligations
    motorcycle      (12), --
    roadSideSource  (13), -- For infrastructure generated calls such as
                          -- fire house, rail infrastructure, roadwork site, etc.
    police          (14), --
    fire            (15), --
    ambulance       (16), -- (does not include private para-transit etc.)
    dot             (17), -- all roadwork vehicles
    transit         (18), -- all transit vehicles 
    slowMoving      (19), -- to also include oversize etc.
    stopNgo         (20), -- to include trash trucks, school buses and others
                          -- that routinely disturb the free flow of traffic
    cyclist         (21), --
    pedestrian      (22), -- also includes those with mobility limitations
    nonMotorized    (23), -- other, horse drawn, etc.
    military        (24), --
    ...  -- (range 0..31)
    }
 
 
 
-- DE_BrakeAppliedPressure (Desc Name) Record 19
BrakeAppliedPressure ::= ENUMERATED {
   unavailable  (0),  -- B'0000 Not Equipped
                      -- or Brake Pres status is unavailable
   minPressure  (1),  -- B'0001 Minimum Braking Pressure
   bkLvl-2      (2),  -- B'0010
   bkLvl-3      (3),  -- B'0011   
   bkLvl-4      (4),  -- B'0100  
   bkLvl-5      (5),  -- B'0101
   bkLvl-6      (6),  -- B'0110
   bkLvl-7      (7),  -- B'0111
   bkLvl-8      (8),  -- B'1000
   bkLvl-9      (9),  -- B'1001
   bkLvl-10     (10), -- B'1010
   bkLvl-11     (11), -- B'1011
   bkLvl-12     (12), -- B'1100
   bkLvl-13     (13), -- B'1101
   bkLvl-14     (14), -- B'1110
   maxPressure  (15)  -- B'1111 Maximum Braking Pressure
   }  -- Encoded as a 4 bit value
 
 
 
-- DE_BrakeAppliedStatus (Desc Name) Record 20
BrakeAppliedStatus ::= BIT STRING {
   unavailable (0),  -- When set, the brake applied status is unavailable
   leftFront   (1),  -- Left Front Active
   leftRear    (2),  -- Left Rear Active
   rightFront  (3),  -- Right Front Active
   rightRear   (4)   -- Right Rear Active
   } (SIZE (5))
 
 
 
-- DE_BrakeBoostApplied (Desc Name) Record 21
BrakeBoostApplied ::= ENUMERATED {
   unavailable   (0), -- Vehicle not equipped with brake boost
                      -- or brake boost data is unavailable
   off           (1), -- Vehicle's brake boost is off
   on            (2)  -- Vehicle's brake boost is on (applied)
   }
 
 
 
-- DE_BumperHeight (Desc Name) Record 22
BumperHeight ::= INTEGER (0..127) -- in units of 0.01 meters from ground surface.
 
 
 
-- DE_J1939-71-Cargo Weight (Desc Name) Record 23
CargoWeight ::= INTEGER (0..65535)
 
 
 
-- DE_CoarseHeading (Desc Name) Record 24
CoarseHeading ::= INTEGER (-128..127) 
   -- where the LSB is in units of 1.5 degrees 
   -- over a range of +- 190.5 degrees 
   -- value -128 shall be used for unavailable
   -- Note that this is not an offset value
 
 
 
-- DE_CodeWord (Desc Name) Record 25
CodeWord ::= OCTET STRING (SIZE(1..16)) 
   -- any octect string up to 16 octets
 
 
 
-- DE_CoefficientOfFriction (Desc Name) Record 26
CoefficientOfFriction ::= INTEGER (0..50) 
   -- where 0 = 0.00 micro (frictonless)
   -- and  50 = 1.00 micro, in steps of 0.02
 
 
 
-- DE_Confidence (Desc Name) Record 27
Confidence ::= INTEGER (0..200)
   -- LSB units of 0.5 percent
 
 
 
-- DE_Count (Desc Name) Record 28
Count ::= INTEGER (0..32)
 
 
 
-- DE_DDay (Desc Name) Record 29
DDay ::= INTEGER (0..31)  -- units of days
 
 
 
-- DE_DeltaAngle (Desc Name) Record 30
DeltaAngle ::= INTEGER (-150..150) 
   -- With an angle range from 
   -- negative 150 to positive 150 
   -- in one degree steps where zero is directly
   -- along the axis or the lane center line as defined by the
   -- two closest points
 
 
 
-- DE_DeltaTime (Desc Name) Record 31
DeltaTime ::= INTEGER (-121 .. 121) 
   -- Supporting a range of +/- 20 minute in steps of 10 seconds
   -- the value of -121 shall be used when more then -20 minutes
   -- the value of +120 shall be used when more then +20 minutes
   -- the value -122 shall be used when the value is unavailable
 
 
 
-- DE_DescriptiveName (Desc Name) Record 32
DescriptiveName ::= IA5String (SIZE(1..63))
 
 
 
-- DE_DHour (Desc Name) Record 33
DHour ::= INTEGER (0..31) -- units of hours
 
 
 
-- DE_DirectionOfUse (Desc Name) Record 34
DirectionOfUse ::= ENUMERATED {
   unavailable (0), -- unknown or NA, not typically used in valid expressions
   forward     (1), -- direction of travel follows node ordering 
   reverse     (2), -- direction of travel is the reverse of node ordering 
   both        (3)  -- direction of travel allowed in both directions 
   }
 
 
 
-- DE_DisabilityType (Desc Name) Record 35
DisabilityType ::= BIT STRING {
   visionImpair         (0),
   hearingImpair        (1),
   movementLimitation   (2),
   mentalHealth         (3)
   } (SIZE (4, ...))
 
 
 
-- DE_DistanceUnits (Desc Name) Record 36
DistanceUnits ::= ENUMERATED {
   centimeter  (0),  
   cm2-5       (1), -- Steps of 2.5 centimeters
   meter       (2),
   decimeter   (3),
   kilometer   (4),
   foot        (5), -- US foot, 0.3048 meters exactly
   yard        (6), -- three US feet
   mile        (7)  -- US mile (5280 US feet)
   }
 
 
 
-- DE_DMinute (Desc Name) Record 37
DMinute ::= INTEGER (0..63) -- units of minutes
 
 
 
-- DE_DMonth (Desc Name) Record 38
DMonth ::= INTEGER (0..15) -- units of months
 
 
 
-- DE_DOffset (Desc Name) Record 39
DOffset ::= INTEGER (-840..840) -- units of minutes from UTC time
 
 
 
-- DE_J1939-71-Drive Axle Lift Air Pressure (Desc Name) Record 40
DriveAxleLiftAirPressure ::= INTEGER (0..1000)
 
 
 
-- DE_J1939-71-Drive Axle Location (Desc Name) Record 41
DriveAxleLocation ::= INTEGER (0..255)
 
 
 
-- DE_J1939-71-Drive Axle Lube Pressure (Desc Name) Record 42
DriveAxleLubePressure ::= INTEGER (0..1000)
 
 
 
-- DE_J1939-71-Drive Axle Temperature (Desc Name) Record 43
DriveAxleTemperature ::= INTEGER (-40..210)
 
 
 
-- DE_DrivenLineOffsetLarge (Desc Name) Record 44
DrivenLineOffsetLg ::= INTEGER (-32767..32767) 
   -- LSB units are 1 cm.
 
 
 
-- DE_DrivenLineOffsetSmall (Desc Name) Record 45
DrivenLineOffsetSm ::= INTEGER (-2047..2047) 
   -- LSB units are 1 cm.
 
 
 
-- DE_DrivingWheelAngle (Desc Name) Record 46
DrivingWheelAngle ::= INTEGER (-127..127) 
   -- LSB units of 0.3333 degrees.  
   -- a range of 42.33 degrees each way
 
 
 
-- DE_DSecond (Desc Name) Record 47
DSecond ::= INTEGER (0..65535) -- units of milliseconds
 
 
 
-- DE_DSRC_MessageID (Desc Name) Record 48
DSRCmsgID ::= INTEGER (0..32767)
   -- 
   -- DER forms, 
   -- All DER forms are now retired and not to be used
   -- 
   reservedMessageId-D               DSRCmsgID ::=  0 --'00'H 
   alaCarteMessage-D                 DSRCmsgID ::=  1 --'01'H ACM
   -- alaCarteMessage-D is Retired, not to be used
   basicSafetyMessage-D              DSRCmsgID ::=  2 --'02'H BSM, heartbeat msg
   basicSafetyMessageVerbose-D       DSRCmsgID ::=  3 --'03'H For testing only
   commonSafetyRequest-D             DSRCmsgID ::=  4 --'04'H CSR
   emergencyVehicleAlert-D           DSRCmsgID ::=  5 --'05'H EVA
   intersectionCollision-D           DSRCmsgID ::=  6 --'06'H ICA
   mapData-D                         DSRCmsgID ::=  7 --'07'H MAP, intersections 
   -- mapData-D is Retired, not to be used
   nmeaCorrections-D                 DSRCmsgID ::=  8 --'08'H NMEA
   probeDataManagement-D             DSRCmsgID ::=  9 --'09'H PDM
   probeVehicleData-D                DSRCmsgID ::= 10 --'0A'H PVD
   roadSideAlert-D                   DSRCmsgID ::= 11 --'0B'H RSA
   rtcmCorrections-D                 DSRCmsgID ::= 12 --'0C'H RTCM
   signalPhaseAndTimingMessage-D     DSRCmsgID ::= 13 --'0D'H SPAT
   -- signalPhaseAndTimingMessage-D is Retired, not to be used
   signalRequestMessage-D            DSRCmsgID ::= 14 --'0E'H SRM
   signalStatusMessage-D             DSRCmsgID ::= 15 --'0F'H SSM
   travelerInformation-D             DSRCmsgID ::= 16 --'10'H TIM
   uperFrame-D                       DSRCmsgID ::= 17 --'11'H UPER frame
   
   --
   -- UPER forms
   --
   mapData                           DSRCmsgID ::=   18 -- MAP, intersections 
   signalPhaseAndTimingMessage       DSRCmsgID ::=   19 -- SPAT
   -- Above two entries were adopted in the 2015-04 edition
   -- Message assignments added in 2015 follow below   
   basicSafetyMessage                DSRCmsgID ::=   20 -- BSM, heartbeat msg
   commonSafetyRequest               DSRCmsgID ::=   21 -- CSR
   intersectionCollision             DSRCmsgID ::=   22 -- ICA
   emergencyVehicleAlert             DSRCmsgID ::=   23 -- ICA
   nmeaCorrections                   DSRCmsgID ::=   24 -- NMEA
   probeDataManagement               DSRCmsgID ::=   25 -- PDM
   probeVehicleData                  DSRCmsgID ::=   26 -- PVD
   roadSideAlert                     DSRCmsgID ::=   27 -- RSA
   rtcmCorrections                   DSRCmsgID ::=   28 -- RTCM
   signalRequestMessage              DSRCmsgID ::=   29 -- SRM
   signalStatusMessage               DSRCmsgID ::=   30 -- SSM
   travelerInformation               DSRCmsgID ::=   31 -- TIM
   personalSafetyMessage             DSRCmsgID ::=   32 -- PSM
                     
   --
   -- The Below values are reserved for local message testing use
   -- 
   testMessage00                     DSRCmsgID ::=  240 -- Hex 0xF0 
   testMessage01                     DSRCmsgID ::=  241  
   testMessage02                     DSRCmsgID ::=  242  
   testMessage03                     DSRCmsgID ::=  243  
   testMessage04                     DSRCmsgID ::=  244   
   testMessage05                     DSRCmsgID ::=  245  
   testMessage06                     DSRCmsgID ::=  246  
   testMessage07                     DSRCmsgID ::=  247  
   testMessage08                     DSRCmsgID ::=  248  
   testMessage09                     DSRCmsgID ::=  249  
   testMessage10                     DSRCmsgID ::=  250 
   testMessage11                     DSRCmsgID ::=  251  
   testMessage12                     DSRCmsgID ::=  252  
   testMessage13                     DSRCmsgID ::=  253  
   testMessage14                     DSRCmsgID ::=  254  
   testMessage15                     DSRCmsgID ::=  255-- Hex 0xFF  
   --
   -- All other values are reserved for std use
   --
 
 
 
-- DE_Duration (Desc Name) Record 49
Duration ::= INTEGER (0..3600) -- units of seconds
 
 
 
-- DE_DYear (Desc Name) Record 50
DYear ::= INTEGER (0..4095) -- units of years
 
 
 
-- DE_Elevation (Desc Name) Record 51
Elevation ::= INTEGER (-4096..61439) 
    -- In units of 10 cm steps above or below the reference ellipsoid
    -- Providing a range of -409.5 to + 6143.9 meters
    -- The value -4096 shall be used when Unknown is to be sent
 
 
 
-- DE_ElevationConfidence (Desc Name) Record 52
ElevationConfidence ::= ENUMERATED {
   unavailable (0),  -- B'0000  Not Equipped or unavailable
   elev-500-00 (1),  -- B'0001  (500 m)
   elev-200-00 (2),  -- B'0010  (200 m)
   elev-100-00 (3),  -- B'0011  (100 m)
   elev-050-00 (4),  -- B'0100  (50 m)
   elev-020-00 (5),  -- B'0101  (20 m)
   elev-010-00 (6),  -- B'0110  (10 m)
   elev-005-00 (7),  -- B'0111  (5 m)
   elev-002-00 (8),  -- B'1000  (2 m)
   elev-001-00 (9),  -- B'1001  (1 m)
   elev-000-50 (10), -- B'1010  (50 cm)
   elev-000-20 (11), -- B'1011  (20 cm)
   elev-000-10 (12), -- B'1100  (10 cm)
   elev-000-05 (13), -- B'1101  (5 cm)
   elev-000-02 (14), -- B'1110  (2 cm)
   elev-000-01 (15)  -- B'1111  (1 cm)
   }  -- Encoded as a 4 bit value
 
 
 
-- DE_Extent (Desc Name) Record 53
Extent ::= ENUMERATED {
   useInstantlyOnly     (0),
   useFor3meters        (1),
   useFor10meters       (2),
   useFor50meters       (3),
   useFor100meters      (4),
   useFor500meters      (5),
   useFor1000meters     (6),
   useFor5000meters     (7),
   useFor10000meters    (8),
   useFor50000meters    (9),
   useFor100000meters   (10),
   useFor500000meters   (11),
   useFor1000000meters  (12),
   useFor5000000meters  (13),
   useFor10000000meters (14),
   forever              (15)  -- very wide area
   }  -- encode as a 4 bits
 
 
 
-- DE_ExteriorLights (Desc Name) Record 54
ExteriorLights ::= BIT STRING { 
   -- all Lights Off indicated by no bits set
   lowBeamHeadlightsOn       (0), 
   highBeamHeadlightsOn      (1), 
   leftTurnSignalOn          (2), 
   rightTurnSignalOn         (3), 
   hazardSignalOn            (4), 
   automaticLightControlOn   (5),
   daytimeRunningLightsOn    (6), 
   fogLightOn                (7), 
   parkingLightsOn           (8) 
   } (SIZE (9, ...))
 
 
 
-- DE_FurtherInfoID (Desc Name) Record 55
FurtherInfoID ::= OCTET STRING (SIZE(2))
   -- a link to any other incident 
   -- information data that may be available 
   -- in the normal ATIS incident description 
   -- or other messages
 
 
 
-- DE_GNSSstatus (Desc Name) Record 56
GNSSstatus ::= BIT STRING {
   unavailable               (0), -- Not Equipped or unavailable
   isHealthy                 (1),
   isMonitored               (2),
   baseStationType           (3), -- Set to zero if a moving base station,
                                  -- set to one if it is a fixed base station 
   aPDOPofUnder5             (4), -- A dilution of precision greater than 5
   inViewOfUnder5            (5), -- Less than 5 satellites in view
   localCorrectionsPresent   (6), -- DGPS type corrections used
   networkCorrectionsPresent (7)  -- RTK type corrections used
   } (SIZE(8))
 
 
 
-- DE_GrossDistance (Desc Name) Record 57
GrossDistance ::= INTEGER (0..1023) -- Units of 1.00 meters
   -- The value 1023 shall indicate unavailable
 
 
 
-- DE_GrossSpeed (Desc Name) Record 58
GrossSpeed ::= INTEGER (0..31) -- Units of 1.00 m/s
   -- The value 30 shall be used for speeds of 30 m/s or greater (67.1 mph)
   -- The value 31 shall indicate that the speed is unavailable
 
 
 
-- DE_Heading (Desc Name) Record 59
Heading ::= INTEGER (0..28800) 
   -- LSB of 0.0125 degrees
   -- A range of 0 to 359.9875 degrees
 
 
 
-- DE_HeadingConfidence (Desc Name) Record 60
HeadingConfidence ::= ENUMERATED {
   unavailable   (0), -- B'000  Not Equipped or unavailable
   prec10deg     (1), -- B'010  10     degrees
   prec05deg     (2), -- B'011  5      degrees
   prec01deg     (3), -- B'100  1      degrees
   prec0-1deg    (4), -- B'101  0.1    degrees
   prec0-05deg   (5), -- B'110  0.05   degrees
   prec0-01deg   (6), -- B'110  0.01   degrees
   prec0-0125deg (7)  -- B'111  0.0125 degrees, aligned with heading LSB
   }  -- Encoded as a 3 bit value
 
 
 
-- DE_HeadingSlice (Desc Name) Record 61
HeadingSlice ::= BIT STRING {
   -- Each bit 22.5 degree starting from 
   -- North and moving Eastward (clockwise) as one bit
   -- a value of noHeading means no bits set, while a 
   -- a value of allHeadings means all bits would be set             
      
   from000-0to022-5degrees  (0),   
   from022-5to045-0degrees  (1),   
   from045-0to067-5degrees  (2),   
   from067-5to090-0degrees  (3),   
   
   from090-0to112-5degrees  (4),   
   from112-5to135-0degrees  (5),   
   from135-0to157-5degrees  (6),   
   from157-5to180-0degrees  (7),   
   
   from180-0to202-5degrees  (8),   
   from202-5to225-0degrees  (9),   
   from225-0to247-5degrees  (10),  
   from247-5to270-0degrees  (11),  
   
   from270-0to292-5degrees  (12),  
   from292-5to315-0degrees  (13),  
   from315-0to337-5degrees  (14),  
   from337-5to360-0degrees  (15)  
   }  (SIZE (16))
 
 
 
-- DE_IntersectionID (Desc Name) Record 62
IntersectionID ::= INTEGER (0..65535)
   -- The values zero through 255 are allocated for testing purposes
   -- Note that the value assigned to an intersection will be
   -- unique within a given regional ID only
 
 
 
-- DE_IntersectionStatusObject (Desc Name) Record 63
IntersectionStatusObject ::= BIT STRING {
    manualControlIsEnabled                (0),
      -- Timing reported is per programmed values, etc. but person
      -- at cabinet can manually request that certain intervals are
      -- terminated early (e.g. green).
    stopTimeIsActivated                   (1),
      -- And all counting/timing has stopped.
    failureFlash                          (2), 
      -- Above to be used for any detected hardware failures, 
      -- e.g. conflict monitor as well as for police flash 
    preemptIsActive                       (3),
    transitSignalPriorityIsActive         (4),   
      -- Referred to as TSP
	 
   -- Additional states
    fixedTimeOperation                    (5),
      -- Schedule of signals is based on time only 
      -- (i.e. the state can be calculated)
    trafficDependentOperation             (6),
      -- Operation is based on different levels of traffic parameters 
      -- (requests, duration of gaps or more complex parameters)
    standbyOperation                      (7),
      -- Controller: partially switched off or partially amber flashing
    failureMode                           (8),
      -- Controller has a problem or failure in operation
    off                                   (9),
      -- Controller is switched off
	 
   -- Related to MAP an SPAT bindings
    recentMAPmessageUpdate                (10),
      -- Map revision with content changes
    recentChangeInMAPassignedLanesIDsUsed (11),
      -- Change in MAP's assigned lanes used (lane changes)
      -- Changes in the active lane list description
    noValidMAPisAvailableAtThisTime       (12),
      -- MAP (and various lanes indexes) not available
    noValidSPATisAvailableAtThisTime      (13)
      -- SPAT system is not working at this time
    
    -- Bit values (14,15) reserved at this time and shall be zero
    } (SIZE(16))
 
 
 
-- DE_IsDolly (Desc Name) Record 64
IsDolly ::= BOOLEAN -- When false indicates a trailer unit
 
 
 
-- DE_Iso3833VehicleType (Desc Name) Record 65
Iso3833VehicleType ::= INTEGER (0..100) 
   -- TBD defintion to be added
 
 
 
-- DE_ITIStextPhrase (Desc Name) Record 66
ITIStextPhrase ::= IA5String (SIZE(1..16))
 
 
 
-- DE_LaneAttributes-Barrier (Desc Name) Record 67
LaneAttributes-Barrier ::= BIT STRING {
   -- With bits as defined:
   median-RevocableLane     (0),
                            -- this lane may be activated or not based
                            -- on the current SPAT message contents
                            -- if not asserted, the lane is ALWAYS present
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))
 
 
 
-- DE_LaneAttributes-Bike (Desc Name) Record 68
LaneAttributes-Bike ::= BIT STRING {
   -- With bits as defined:
   bikeRevocableLane       (0),
                           -- this lane may be activated or not based
                           -- on the current SPAT message contents
                           -- if not asserted, the lane is ALWAYS present
   pedestrianUseAllowed    (1),
                           -- The path allows pedestrian traffic, 
                           -- if not set, this mode is prohibited
   isBikeFlyOverLane       (2),
                           -- path of lane is not at grade
   fixedCycleTime          (3),
                           -- the phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
   isolatedByBarrier       (5),
   unsignalizedSegmentsPresent  (6)
                           -- The lane path consists of one of more segments
                           -- which are not part of a signal group ID

   -- Bits 7~15 reserved and set to zero
   } (SIZE (16))
 
 
 
-- DE_LaneAttributes-Crosswalk (Desc Name) Record 69
LaneAttributes-Crosswalk ::= BIT STRING { 
   -- With bits as defined:
   -- MUTCD provides no suitable "types" to use here
   crosswalkRevocableLane  (0),
                           -- this lane may be activated or not based
                           -- on the current SPAT message contents
                           -- if not asserted, the lane is ALWAYS present
   bicyleUseAllowed        (1),
                           -- The path allows bicycle traffic, 
                           -- if not set, this mode is prohibited
   isXwalkFlyOverLane      (2),
                           -- path of lane is not at grade
   fixedCycleTime          (3),
                           -- ped walk phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
   hasPushToWalkButton     (5),
                           -- Has a demand input
   audioSupport            (6),
                           -- audio crossing cues present
   rfSignalRequestPresent  (7),
                           -- Supports RF push to walk technologies
   unsignalizedSegmentsPresent  (8)
                           -- The lane path consists of one of more segments
                           -- which are not part of a signal group ID
   -- Bits 9~15 reserved and set to zero
   } (SIZE (16))
 
 
 
-- DE_LaneAttributes-ParkingLane (Desc Name) Record 70
LaneAttributes-Parking ::= BIT STRING { 
    -- With bits as defined:
    -- Parking use details, note that detailed restrictions such as 
    -- allowed hours are sent by way of ITIS codes in the TIM message
    parkingRevocableLane         (0),
                                 -- this lane may be activated or not based
                                 -- on the current SPAT message contents
                                 -- if not asserted, the lane is ALWAYS present
    parallelParkingInUse         (1),
    headInParkingInUse           (2),
    doNotParkZone                (3),
                                 -- used to denote fire hydrants as well
                                 -- short disruptions in a parking zone
    parkingForBusUse             (4),
    parkingForTaxiUse            (5),
    noPublicParkingUse           (6)
                                 -- private parking, as in front of
                                 -- private property
   -- Bits 7~15 reserved and set to zero
   } (SIZE (16))
 
 
 
-- DE_LaneAttributes-Sidewalk (Desc Name) Record 71
LaneAttributes-Sidewalk ::= BIT STRING { 
   -- With bits as defined:
   sidewalk-RevocableLane  (0),
                           -- this lane may be activated or not based
                           -- on the current SPAT message contents
                           -- if not asserted, the lane is ALWAYS present
   bicyleUseAllowed        (1),
                           -- The path allows bicycle traffic, 
                           -- if not set, this mode is prohibited
   isSidewalkFlyOverLane   (2),
                           -- path of lane is not at grade
   walkBikes               (3)
                           -- bike traffic must dismount and walk
   -- Bits 4~15 reserved and set to zero
   } (SIZE (16))
 
 
 
-- DE_LaneAttributes-Striping (Desc Name) Record 72
LaneAttributes-Striping ::= BIT STRING { 
   -- With bits as defined:
    stripeToConnectingLanesRevocableLane      (0),
       -- this lane may be activated or not activated based
       -- on the current SPAT message contents
       -- if not asserted, the lane is ALWAYS present
    stripeDrawOnLeft                          (1),
    stripeDrawOnRight                         (2),
        -- which side of lane to mark
    stripeToConnectingLanesLeft               (3),
    stripeToConnectingLanesRight              (4),
    stripeToConnectingLanesAhead              (5)
        -- the stripe type should be
        -- presented to the user visually
        -- to reflect stripes in the 
        -- intersection for the type of
        -- movement indicated
   -- Bits 6~15 reserved and set to zero
   } (SIZE (16))
 
 
 
-- DE_LaneAttributes-TrackedVehicle (Desc Name) Record 73
LaneAttributes-TrackedVehicle ::= BIT STRING { 
   -- With bits as defined:
   spec-RevocableLane         (0),
                               -- this lane may be activated or not based
                               -- on the current SPAT message contents
                               -- if not asserted, the lane is ALWAYS present
   spec-commuterRailRoadTrack (1), 
   spec-lightRailRoadTrack    (2),
   spec-heavyRailRoadTrack    (3),
   spec-otherRailType         (4)
   -- Bits 5~15 reserved and set to zero
   } (SIZE (16))
 
 
 
-- DE_LaneAttributes-Vehicle (Desc Name) Record 74
LaneAttributes-Vehicle ::= BIT STRING {  
   -- With bits as defined:
   isVehicleRevocableLane       (0),
                                 -- this lane may be activated or not based
                                 -- on the current SPAT message contents
                                 -- if not asserted, the lane is ALWAYS present
   isVehicleFlyOverLane         (1),
                                 -- path of lane is not at grade
   hovLaneUseOnly               (2),
   restrictedToBusUse           (3),
   restrictedToTaxiUse          (4),
   restrictedFromPublicUse      (5),
   hasIRbeaconCoverage          (6)

   -- Bits 7~15 reserved and set to zero
   } (SIZE (16))
 
 
 
-- DE_LaneConnectionID (Desc Name) Record 75
LaneConnectionID ::= INTEGER (0..255)
 
 
 
-- DE_LaneDirection (Desc Name) Record 76
LaneDirection ::= BIT STRING {
   -- With bits as defined:
   -- Allowed directions of travel in the lane object
   -- All lanes are described from the stop line outwards
   ingressPath     (0), 
                   -- travel from rear of path to front 
                   -- is allowed
   egressPath      (1)
                   -- travel from front of path to rear 
                   -- is allowed
   -- Notes:  No Travel, i.e. the lane object type does not support
   --         travel (medians, curbs, etc.) is indicated by not 
   --         asserting any bit value
   --         Bi-Directional Travel (such as a ped crosswalk) is 
   --         indicated by asserting both of the bits
   } (SIZE (2))
 
 
 
-- DE_LaneId (Desc Name) Record 77
LaneID ::= INTEGER (0..255)
   -- the value 0 shall be used when the lane ID is
   -- not available or not known
   -- the value 255 is reserved for future use
 
 
 
-- DE_LaneSharing (Desc Name) Record 78
LaneSharing ::= BIT STRING {
    -- With bits as defined:
    overlappingLaneDescriptionProvided  (0),
    -- Assert when another lane object is present to describe the
    -- path of the overlapping shared lane
    -- this construct is not used for lane objects which simply cross
    multipleLanesTreatedAsOneLane       (1),
    -- Assert if the lane object path and width details represents
    -- multiple lanes within it that are not further described

    -- Various modes and type of traffic whhc may share this lane:
    otherNonMotorizedTrafficTypes       (2), -- horse drawn etc.
    individualMotorizedVehicleTraffic   (3),
    busVehicleTraffic                   (4),  
    taxiVehicleTraffic                  (5),
    pedestriansTraffic                  (6),
    cyclistVehicleTraffic               (7),
    trackedVehicleTraffic               (8),
    pedestrianTraffic                   (9)
    } (SIZE (10))
    -- All zeros would indicate 'not shared' and 'not overlapping'
 
 
 
-- DE_LaneWidth (Desc Name) Record 79
LaneWidth ::= INTEGER (0..32767) -- units of 1 cm
 
 
 
-- DE_Latitude (Desc Name) Record 80
Latitude ::= INTEGER (-900000000..900000001)  
   -- LSB = 1/10 micro degree
   -- Providing a range of plus-minus 90 degrees
 
 
 
-- DE_LayerID (Desc Name) Record 81
LayerID ::= INTEGER (0..100)
 
 
 
-- DE_LayerType (Desc Name) Record 82
LayerType ::= ENUMERATED {
     none, 
     mixedContent, -- two or more of the below types
     generalMapData, 
     intersectionData, 
     curveData, 
     roadwaySectionData, 
     parkingAreaData, 
     sharedLaneData,
     ... 
     }
 
 
 
-- DE_LightbarInUse (Desc Name) Record 83
LightbarInUse ::= ENUMERATED {
     unavailable         (0),  -- Not Equipped or unavailable
     notInUse            (1),  -- none active
     inUse               (2),  
     sirenInUse          (3),   
     yellowCautionLights (4),  
     schooldBusLights    (5),  
     arrowSignsActive    (6),  
     slowMovingVehicle   (7),   
     freqStops           (8),   
     reserved            (9)  -- for future use
     }
 
 
 
-- DE_MAYDAY_Location_quality_code (Desc Name) Record 84
Location-quality ::= ENUMERATED {                        
     loc-qual-bt1m       (0), -- quality better than 1 meter
     loc-qual-bt5m       (1), -- quality better than 5 meters
     loc-qual-bt12m      (2), -- quality better than 12.5 meters
     loc-qual-bt50m      (3), -- quality better than 50 meters
     loc-qual-bt125m     (4), -- quality better than 125 meters
     loc-qual-bt500m     (5), -- quality better than 500 meters
     loc-qual-bt1250m    (6), -- quality better than 1250 meters
     loc-qual-unknown    (7)  -- quality value unknown
     } -- 3 bits, appends with loc-tech to make one octet (0..7)
 
 
 
-- DE_MAYDAY_Location_tech_code (Desc Name) Record 85
Location-tech ::= ENUMERATED {                        
     loc-tech-unknown    (0), -- technology type unknown
     loc-tech-GNSS       (1), -- GNSS technology only
     loc-tech-DGPS       (2), -- differential GNSS (DGPS) technology
     loc-tech-drGPS      (3), -- dead reckoning system w/GPS
     loc-tech-drDGPS     (4), -- dead reckoning system w/DGPS
     loc-tech-dr         (5), -- dead reckoning only
     loc-tech-nav        (6), -- autonomous navigation system on-board
     ...,
     loc-tech-fault      (31) -- feature is not working
     }    -- (0..31) 5 bits, appends with loc-quality to make one octet
 
 
 
-- DE_Longitude (Desc Name) Record 86
Longitude ::= INTEGER (-1799999999..1800000001)  
   -- LSB = 1/10 micro degree
   -- Providing a range of plus-minus 180 degrees
 
 
 
-- DE_MergeDivergeNodeAngle (Desc Name) Record 87
MergeDivergeNodeAngle ::= INTEGER (-180..180) 
   -- In units of 1.5 degrees for north
   -- the value -180 shall be used to represent 
   -- data is not available or unknown
 
 
 
-- DE_MessageBLOB (Desc Name) Record 88
MessageBLOB ::= OCTET STRING (SIZE(10..2000)) 
    -- Final size range may be further 
    -- limited by the transport layer used
 
 
 
-- DE_MinuteOfTheYear (Desc Name) Record 89
MinuteOfTheYear ::= INTEGER (0..527040) 
   -- the value 527040 shall be used for invalid
 
 
 
-- DE_MinutesDuration (Desc Name) Record 90
MinutesDuration ::= INTEGER (0..32000) -- units of minutes
 
 
 
-- DE_MotorizationType (Desc Name) Record 91
MotorizationType ::= BIT STRING {   
   motorized      (0),
   horseback      (1),
   horseCarridge  (2)
   }  (SIZE (3, ...))
 
 
 
-- DE_MovementPhaseState (Desc Name) Record 92
MovementPhaseState ::= ENUMERATED {
    -- Note that based on the regions and the operating mode not every 
    -- phase will be used in all transportation modes and that not 
    -- every phase will be used in all transportation modes
  
    unavailable (0), 
      -- This state is used for unknown or error 
    dark (1),   
      -- The signal head is dark (unlit)

   -- Reds
    stop-Then-Proceed (2), 
      -- Often called 'flashing red' in US
      -- Driver Action:                     
      --   Stop vehicle at stop line. 
      --   Do not proceed unless it is safe.
      -- Note that the right to proceed either right or left when 
      -- it is safe may be contained in the lane description to 
      -- handle what is called a 'right on red'
    stop-And-Remain (3),
      -- e.g. called 'red light' in US
      -- Driver Action:                     
      --   Stop vehicle at stop line. 
      --   Do not proceed.                     
      -- Note that the right to proceed either right or left when 
      -- it is safe may be contained in the lane description to 
      -- handle what is called a 'right on red'
   
   -- Greens
    pre-Movement (4), 
      -- Not used in the US, red+yellow partly in EU
      -- Driver Action:                     
      --   Stop vehicle. 
      --   Prepare to proceed (pending green)
      --   (Prepare for transition to green/go)
    permissive-Movement-Allowed (5), 
      -- Often called 'permissive green' in US
      -- Driver Action:                     
      --   Proceed with caution, 
      --   must yield to all conflicting traffic 
      -- Conflicting traffic may be present
      -- in the intersection conflict area
    protected-Movement-Allowed (6), 
      -- Often called 'protected green' in US
      -- Driver Action:                     
      --   Proceed, tossing caution to the wind, 
      --   in indicated (allowed) direction.
   
   -- Yellows / Ambers
   -- The vehicle is not allowed to cross the stop bar if it is possible 
   -- to stop without danger. 
    permissive-clearance (7), 
      -- Often called 'permissive yellow' in US
      -- Driver Action:                     
      --   Prepare to stop.
      --   Proceed if unable to stop,
      --   Clear Intersection.
      -- Conflicting traffic may be present
      -- in the intersection conflict area
    protected-clearance (8),  
      -- Often called 'protected yellow' in US
      -- Driver Action: 
      --   Prepare to stop.
      --   Proceed if unable to stop,
      --   in indicated direction (to connected lane)
      --   Clear Intersection.
                    
    caution-Conflicting-Traffic (9)
      -- Often called 'flashing yellow' in US
      -- Often used for extended periods of time
      -- Driver Action: 
      --   Proceed with caution, 
      -- Conflicting traffic may be present
      -- in the intersection conflict area
    }
    -- The above number assignments are not used with UPER encoding
    -- and are only to be used with DER or implicit encoding
 
 
 
-- DE_MsgCount (Desc Name) Record 93
MsgCount ::= INTEGER (0..127)
 
 
 
-- DE_MsgCRC (Desc Name) Record 94
MsgCRC ::= OCTET STRING (SIZE(2)) -- created with the CRC-CCITT polynomial
 
 
 
-- DE_MultiVehicleResponse (Desc Name) Record 95
MultiVehicleResponse ::= ENUMERATED {
     unavailable   (0), -- Not Equipped or unavailable
     singleVehicle (1),  
     multiVehicle  (2),  
     reserved      (3)  -- for future use
     }
 
 
 
-- DE_MUTCDCode (Desc Name) Record 96
MUTCDCode ::= ENUMERATED {
   none            (0), -- non-MUTCD information 
   regulatory      (1), -- "R" Regulatory signs
   warning         (2), -- "W" warning signs
   maintenance     (3), -- "M" Maintenance and construction 
   motoristService (4), -- Motorist Services
   guide           (5), -- "G" Guide signs
   rec             (6), -- Recreation and Cultural Interest 
   ...  
   }  -- values to 127 reserved for std use
      -- values 128 to 255 reserved for local use
 
 
 
-- DE_NMEA_MsgType (Desc Name) Record 97
NMEA-MsgType ::= INTEGER (0..32767)
 
 
 
-- DE_NMEA_Payload (Desc Name) Record 98
NMEA-Payload ::= OCTET STRING (SIZE(1..1023))
 
 
 
-- DE_NMEA_Revision (Desc Name) Record 99
NMEA-Revision ::= ENUMERATED {
     unknown       (0), -- default value
     reserved      (1),
     rev1          (2),
     rev2          (3), -- used for 2.x
     rev3          (4),
     rev4          (5),
     rev5          (6),
     ...  
     }
 
 
 
-- DE_NodeAttributeLL (Desc Name) Record 100
NodeAttributeLL ::= ENUMERATED {
--
--   FIX ME FIX ME
--
--
   -- Various values which pertain only to the current node point
   
   -- General Items
   reserved,  
   stopLine,             -- point where a mid-path stop line exists
                         -- See also 'do not block' for segments

   -- Path finish details 
   roundedCapStyleA,      -- Used to control final path rounded end shape
                          -- with edge of curve at final point in a circle
   roundedCapStyleB,      -- Used to control final path rounded end shape
                          -- with edge of curve extending 50% of width past
                          -- final point in a circle
   
   -- Topography Points (items with no concept of a distance along the path)
   mergePoint,           -- Japan merge with 1 or more lanes
   divergePoint,         -- Japan diverge with 1 or more lanes
   downstreamStopLine,   -- Japan style downstream intersection 
                                   -- (a 2nd intersection) stop line
   downstreamStartNode,  -- Japan style downstream intersection 
                                   -- (a 2nd intersection) start node
     
   -- Pedestrian Support Attributes
   closedToTraffic,      -- where a pedestrian may NOT go
                         -- to be used during construction events
   safeIsland,           -- a pedestrian safe stopping point
                         -- also called a traffic island
                         -- This usage described a point feature on a path, 
                         -- other entries can describe a path
   curbPresentAtStepOff, -- the sidewalk to street curb is NOT 
                         -- angled where it meets the edge of the 
                         -- roadway (user must step up/down)
 
   -- Lane geometry details  (see standard for defined shapes)
   hydrantPresent,       -- Or other services access 
   ...
   }
 
 
 
-- DE_NodeAttributeXY (Desc Name) Record 101
NodeAttributeXY ::= ENUMERATED {
   -- Various values which pertain only to the current node point
   
   -- General Items
   reserved,  
   stopLine,             -- point where a mid-path stop line exists
                         -- See also 'do not block' for segments

   -- Path finish details 
   roundedCapStyleA,      -- Used to control final path rounded end shape
                          -- with edge of curve at final point in a circle
   roundedCapStyleB,      -- Used to control final path rounded end shape
                          -- with edge of curve extending 50% of width past
                          -- final point in a circle
   
   -- Topography Points (items with no concept of a distance along the path)
   mergePoint,           -- Japan merge with 1 or more lanes
   divergePoint,         -- Japan diverge with 1 or more lanes
   downstreamStopLine,   -- Japan style downstream intersection 
                                   -- (a 2nd intersection) stop line
   downstreamStartNode,  -- Japan style downstream intersection 
                                   -- (a 2nd intersection) start node
     
   -- Pedestrian Support Attributes
   closedToTraffic,      -- where a pedestrian may NOT go
                         -- to be used during construction events
   safeIsland,           -- a pedestrian safe stopping point
                         -- also called a traffic island
                         -- This usage described a point feature on a path, 
                         -- other entries can describe a path
   curbPresentAtStepOff, -- the sidewalk to street curb is NOT 
                         -- angled where it meets the edge of the 
                         -- roadway (user must step up/down)
 
   -- Lane geometry details  (see standard for defined shapes)
   hydrantPresent,       -- Or other services access 
   ...
   }
 
 
 
-- DE_ObjectCount (Desc Name) Record 102
ObjectCount ::= INTEGER (0..1023) -- a count of objects
 
 
 
-- DE_ObstacleDirection (Desc Name) Record 103
ObstacleDirection ::= Angle -- Use the header DE for this unless it proves different.
 
 
 
-- DE_ObstacleDistance (Desc Name) Record 104
ObstacleDistance ::= INTEGER (0..32767) -- LSB units of meters
 
 
 
-- DE_Offset_B09 (Desc Name) Record 105
Offset-B09 ::= INTEGER (-256..255)
   -- a range of +- 2.55 meters
 
 
 
-- DE_Offset_B10 (Desc Name) Record 106
Offset-B10 ::= INTEGER (-512..511)
   -- a range of +- 5.11 meters
 
 
 
-- DE_Offset_B11 (Desc Name) Record 107
Offset-B11 ::= INTEGER (-1024..1023)
   -- a range of +- 10.23 meters
 
 
 
-- DE_Offset_B12 (Desc Name) Record 108
Offset-B12 ::= INTEGER (-2048..2047)
   -- a range of +- 20.47 meters
 
 
 
-- DE_Offset_B13 (Desc Name) Record 109
Offset-B13 ::= INTEGER (-4096..4095)
   -- a range of +- 50.95 meters
 
 
 
-- DE_Offset_B14 (Desc Name) Record 110
Offset-B14 ::= INTEGER (-8192..8191)
   -- a range of +- 81.91 meters
 
 
 
-- DE_Offset_B16 (Desc Name) Record 111
Offset-B16 ::= INTEGER (-32768..32767)
   -- a range of +- 327.68 meters
 
 
 
-- DE_OffsetLL-B12 (Desc Name) Record 112
OffsetLL-B12 ::= INTEGER (-2048..2047)     
   -- a range of +- 0.0002047 degrees
   -- a range of +- 22.634554 meters at the equator
 
 
 
-- DE_OffsetLL-B14 (Desc Name) Record 113
OffsetLL-B14 ::= INTEGER (-8192..8191)     
   -- a range of +- 0.0008191 degrees
   -- a range of +- 90.571389 meters at the equator
 
 
 
-- DE_OffsetLL-B16 (Desc Name) Record 114
OffsetLL-B16 ::= INTEGER (-32768..32767)     
   -- a range of +- 0.0032767 degrees
   -- a range of +- 362.31873 meters at the equator
 
 
 
-- DE_OffsetLL-B18 (Desc Name) Record 115
OffsetLL-B18 ::= INTEGER (-131072..131071)     
   -- a range of +- 0.0131071 degrees
   -- a range of +- 01.449308 Kmeters at the equator
 
 
 
-- DE_OffsetLL-B22 (Desc Name) Record 116
OffsetLL-B22 ::= INTEGER (-2097152..2097151)     
   -- a range of +- 0.2097151 degrees
   -- a range of +- 23.189096 Kmeters at the equator
 
 
 
-- DE_OffsetLL-B24 (Desc Name) Record 117
OffsetLL-B24 ::= INTEGER (-8388608..8388607)     
   -- a range of +- 0.8388607 degrees
   -- a range of +- 92.756481 Kmeters at the equator
 
 
 
-- DE_PayloadData (Desc Name) Record 118
PayloadData ::= OCTET STRING (SIZE(1..2048))
 
 
 
-- DE_PedestrianBicycleDetect (Desc Name) Record 119
PedestrianBicycleDetect ::= BOOLEAN -- 
                 -- true if ANY Pedestrians or Bicyclists are 
                 -- detected crossing the target lane or lanes
 
 
 
-- DE_PersonalClusterRadius (Desc Name) Record 120
PersonalClusterRadius ::= INTEGER (0..100) -- units of meters
 
 
 
-- DE_NumberOfParticipantsInCluster (Desc Name) Record 121
PersonalClusterSize ::= ENUMERATED { 
   unavailable  (0),
   small        (1),   -- 2-5
   medium       (2),   -- 6-10
   large        (3),   -- >10
   ...
   }
 
 
 
-- DE_PersonalCrossingInProgress (Desc Name) Record 122
PersonalCrossingInProgress ::= BOOLEAN -- Use:
   -- True  = Yes, is in maneuver
   -- False = No
 
 
 
-- DE_PersonalCrossingRequest (Desc Name) Record 123
PersonalCrossingRequest ::= BOOLEAN -- Use:
   -- True  = On  (request crossing)
   -- False = Off (no request)
 
 
 
-- DE_PersonalDeviceUsageState (Desc Name) Record 124
PersonalDeviceUsageState ::= BIT STRING {  
   idle             (0),   
   listeningToMusic (1),   
   typing           (2), -- Including texting, entering addresses 
                         -- and other manual input activity 
   calling          (3),   
   playingGames     (4),   
   reading          (5),   
   viewing          (6), -- Watching dynamic contents, including following 
                         -- navigation prompts, viewing videos and other 
                         -- visual contents that are not static
   other            (7) 
   } (SIZE (8, ...))
   -- All bits shall be set to zero when unknown state
 
 
 
-- DE_PersonalDeviceUserType (Desc Name) Record 125
PersonalDeviceUserType ::= ENUMERATED { 
   unavailable           (0),
   aPEDESTRIAN           (1),
   aPEDALCYCLIST         (2),
   aPUBLICSAFETYWORKER   (3),
   anANIMAL              (4),
   ...
   }
 
 
 
-- DE_PersonalMovementState (Desc Name) Record 126
PersonalMovementState ::= BIT STRING {
   stationary    (0),
   waiting       (1),  -- (longer than 3 seconds in stationary)
   walking       (2),  -- speeds of up to 2.5 m/s
                       -- walking for pedestrian on foot, and "rolling" for
                       -- pedestrians and other type of vulnerable road users 
                       -- such as skateboards
   running       (3),  -- speeds of greater than 2.5 m/s
   playing       (4)   -- (run-to-stop, stop-to-run, etc)    
   } (SIZE (5, ...))
 
 
 
-- DE_PersonalOnWheelType (Desc Name) Record 127
PersonalOnWheelType ::= ENUMERATED { 
   unavailable         (0),
   skateboard          (1),
   pushOrKickScoooter  (2),
   ...
   }
 
 
 
-- DE_PivotingAllowed (Desc Name) Record 128
PivotingAllowed ::= BOOLEAN 
 
 
 
-- DE_PositionConfidence (Desc Name) Record 129
PositionConfidence ::= ENUMERATED {
   unavailable (0),  -- B'0000  Not Equipped or unavailable
   a500m   (1), -- B'0001  500m  or about 5 * 10 ^ -3 decimal degrees
   a200m   (2), -- B'0010  200m  or about 2 * 10 ^ -3 decimal degrees
   a100m   (3), -- B'0011  100m  or about 1 * 10 ^ -3 decimal degrees
   a50m    (4), -- B'0100  50m   or about 5 * 10 ^ -4 decimal degrees 
   a20m    (5), -- B'0101  20m   or about 2 * 10 ^ -4 decimal degrees 
   a10m    (6), -- B'0110  10m   or about 1 * 10 ^ -4 decimal degrees 
   a5m     (7), -- B'0111  5m    or about 5 * 10 ^ -5 decimal degrees 
   a2m     (8), -- B'1000  2m    or about 2 * 10 ^ -5 decimal degrees 
   a1m     (9), -- B'1001  1m    or about 1 * 10 ^ -5 decimal degrees 
   a50cm  (10), -- B'1010  0.50m or about 5 * 10 ^ -6 decimal degrees 
   a20cm  (11), -- B'1011  0.20m or about 2 * 10 ^ -6 decimal degrees 
   a10cm  (12), -- B'1100  0.10m or about 1 * 10 ^ -6 decimal degrees 
   a5cm   (13), -- B'1101  0.05m or about 5 * 10 ^ -7 decimal degrees 
   a2cm   (14), -- B'1110  0.02m or about 2 * 10 ^ -7 decimal degrees 
   a1cm   (15)  -- B'1111  0.01m or about 1 * 10 ^ -7 decimal degrees 
   } 
   -- Encoded as a 4 bit value
 
 
 
-- DE_PrioritizationResponseStatus (Desc Name) Record 130
PrioritizationResponseStatus ::= ENUMERATED {
   unknown           (0),
                      -- Unknown state
   requested         (1),
                      -- This prioritization request was detected 
                      -- by the traffic controller  
   processing        (2),
                      -- Checking request 
                      -- (request is in queue, others requests are prior)
   watchOtherTraffic (3),
                      -- Cannot give full permission, 
                      -- therefore watch for other traffic
                      -- Note that other requests may be present
   granted           (4),
                      -- Intervention was successful 
                      -- and now prioritization is active
   rejected          (5),
                      -- The prioritization or preemption request was 
                      -- rejected by the traffic controller
   maxPresence       (6),
                      -- The Request has exceeded maxPresence time
                      -- Used when the controller has determined that
                      -- The requester should then back off and 
                      -- request an alternative.  
   reserviceLocked   (7),
                      -- Prior conditions have resulted in a reservice 
                      -- locked event: the controller requires the 
                      -- passage of time before another similar request 
                      -- will be accepted
   ...
   }
 
 
 
-- DE_Priority (Desc Name) Record 131
Priority ::= OCTET STRING (SIZE(1)) 
    -- Follow definition notes on setting these bits
 
 
 
-- DE_PriorityRequestType (Desc Name) Record 132
PriorityRequestType ::= ENUMERATED {
     priorityRequestTypeReserved (0),  
     priorityRequest             (1),   
     priorityRequestUpdate       (2), 
     priorityCancellation        (3),  
     ...  
     }
 
 
 
-- DE_PrivilegedEventFlags (Desc Name) Record 133
PrivilegedEventFlags ::= BIT STRING {
   -- These values require a suitable SSP to be sent
   peUnavailable                (0), -- Not Equipped or unavailable
   peEmergencyResponse          (1),
      -- The vehicle is a properly authorized public safety vehicle, 
      -- is engaged in a service call, and is currently moving 
      -- or is within the roadway.  Note that lights and sirens 
      -- may not be evident during any givern response call   

   -- Emergency and Non Emergency Lights related
   peEmergencyLightsActive      (2),
   peEmergencySoundActive       (3),
   peNonEmergencyLightsActive   (4),
   peNonEmergencySoundActive    (5)

   -- this list is likley to grow with further peer review
   } (SIZE (8))
 
 
 
-- DE_ProbeSegmentNumber (Desc Name) Record 134
ProbeSegmentNumber ::= INTEGER (0..32767)  
   -- value determined by local device 
   -- as per standard
 
 
 
-- DE_PublicSafetyAndRoadWorkerActivity (Desc Name) Record 135
PublicSafetyAndRoadWorkerActivity ::= BIT STRING {
   unavailable          (0),
   workingOnRoad        (1),
   settingUpClosures    (2),
   respondingToEvents   (3),
   directingTraffic     (4),
   otherActivities      (5)  -- designated by regional authorities  
   } (SIZE (6, ...))
 
 
 
-- DE_PublicSafetyDirectingTrafficSubType (Desc Name) Record 136
PublicSafetyDirectingTrafficSubType ::= BIT STRING {
   unavailable                        (0),
   policeAndTrafficOfficers           (1), 
   trafficControlPersons              (2), 
   -- on utility, maintenance or construction projects
   railroadCrossingGuards             (3), 
   -- at railroad grade crossings, 
   -- for purposes of stopping vehicular traffic 
   -- to permit the safe passage of trains
   civilDefenseNationalGuardMilitaryPolice (4), 
   -- while performing their regular duties or during National 
   -- or local emergencies
   emergencyOrganizationPersonnel     (5), 
   -- Personnel belonging to emergency organizations such as 
   -- fire departments, hospitals, river rescue associations, 
   -- ambulance associations and personnel of emergency vehicles 
   -- as designated by the regional authority 
   -- (relating to designation of emergency vehicles) 
   -- while performing their duties.
   highwayServiceVehiclePersonnel     (6) 
   -- Associated with tow trucks and road service vehicles.
   } (SIZE (7, ...))
 
 
 
-- DE_PublicSafetyEventResponderType (Desc Name) Record 137
PublicSafetyEventResponderType ::= ENUMERATED { 
   unavailable             (0),
   towOperater             (1),
   fireAndEMSWorker        (2),
   aDOTWorker              (3),
   lawEnforcement          (4),
   toxicSubstance          (5),
   animalControl           (6),
   otherPersonnel          (7),
   ...
   }
 
 
 
-- DE_Radius (Desc Name) Record 138
Radius-B12 ::= INTEGER (0..4095)
   -- with the LSB unit value determined elsewhere
   -- the value 4095 shall be used for unknown
 
 
 
-- DE_RadiusOfCurvature (Desc Name) Record 139
RadiusOfCurvature ::= INTEGER (-32767..32767)
   -- LSB units of 10cm
   -- A straight path to use value of 32767
 
 
 
-- DE_RainSensor (Desc Name) Record 140
RainSensor ::= ENUMERATED {
     none               (0), 
     lightMist          (1), 
     heavyMist          (2), 
     lightRainOrDrizzle (3),
     rain               (4),
     moderateRain       (5),
     heavyRain          (6),
     heavyDownpour      (7) 
     }
 
 
 
-- DE_RegionId (Desc Name) Record 141
RegionId ::= INTEGER (0..255)
   noRegion     RegionId ::= 0  -- Use default supplied stubs
   addGrpA      RegionId ::= 1  -- USA
   addGrpB      RegionId ::= 2  -- Japan
   addGrpC      RegionId ::= 3  -- EU
   -- NOTE: new registered regional IDs will be added here
   -- The values 128 and above are for local region use
 
 
 
-- DE_RequestedItem (Desc Name) Record 142
RequestedItem ::= ENUMERATED {
   reserved      (0),
   itemA         (1),
        -- consisting of 2 elements: 
        -- lights          ExteriorLights 
        -- lightBar        LightbarInUse 
   
   itemB         (2),
        -- consisting of: 
        -- wipers  a SEQUENCE
   
   itemC         (3),
        -- consisting of: 
        -- brakeStatus  BrakeSystemStatus 

   itemD         (4),
        -- consisting of 2 elements: 
        -- brakePressure   BrakeAppliedPressure   
        -- roadFriction    CoefficientOfFriction   
      
   itemE         (5),
        -- consisting of 4 elements: 
        -- sunData         SunSensor                
        -- rainData        RainSensor                   
        -- airTemp         AmbientAirTemperature     
        -- airPres         AmbientAirPressure     
   
   itemF         (6),
        -- consisting of: 
        -- steering  a SEQUENCE 
    
   itemG         (7),
        -- consisting of: 
        -- accelSets a SEQUENCE 
   
   itemH         (8),
        -- consisting of: 
        -- object a SEQUENCE 
   
   
   itemI         (9),
        -- consisting of: 
        -- fullPos         FullPositionVector       
   
   itemJ         (10),
        -- consisting of: 
        -- position2D      Position2D  

   itemK         (11),
        -- consisting of: 
        -- position3D      Position3D 
 
   itemL         (12),
        -- consisting of 2 elements: 
        -- speedHeadC      SpeedandHeadingConfidence     
        -- speedC          SpeedConfidence  
   
   itemM         (13),
        -- consisting of: 
        -- vehicleData a SEQUENCE   
   
   itemN         (14),
        -- consisting of: 
        -- vehicleIdent   VehicleIdent 
   
   itemO         (15),
        -- consisting of: 
        -- weatherReport a SEQUENCE   
   
   itemP         (16),
        -- consisting of: 
        -- breadcrumbs    VehicleMotionTrail 
   
   itemQ         (17),
        -- consisting of: 
        -- GNSSStatus      GNSSstatus      
      
   ...    
   }
   -- values to 127 reserved for std use
   -- values 128 to 255 reserved for local use
 
 
 
-- DE_RequestID (Desc Name) Record 143
RequestID ::= INTEGER (0..255)
 
 
 
-- DE_RequestImportanceLevel (Desc Name) Record 144
RequestImportanceLevel ::= ENUMERATED {
    requestImportanceLevelUnKnown  (0),
    requestImportanceLevel1        (1), -- The least important request
    requestImportanceLevel2        (2), -- The values here shall be assigned
    requestImportanceLevel3        (3), -- Meanings based on regional needs
    requestImportanceLevel4        (4), -- for each of the basic roles which
    requestImportanceLevel5        (5), -- are defined elsewhere
    requestImportanceLevel6        (6),
    requestImportanceLevel7        (7),
    requestImportanceLevel8        (8),
    requestImportanceLevel9        (9),
    requestImportanceLevel10      (10),
    requestImportanceLevel11      (11),
    requestImportanceLevel12      (12),
    requestImportanceLevel13      (13),
    requestImportanceLevel14      (14), -- The most important request
    requestImportanceReserved     (15)  -- Reserved for future use
    }
 
 
 
-- DE_RequestSubRole (Desc Name) Record 145
RequestSubRole ::= ENUMERATED {
    requestSubRoleUnKnown    (0),
    requestSubRole1          (1), -- The first type of sub role
    requestSubRole2          (2), -- The values here shall be assigned
    requestSubRole3          (3), -- Meanings based on regional needs
    requestSubRole4          (4), -- to refine and expand the basic
    requestSubRole5          (5), -- roles which are defined elsewhere
    requestSubRole6          (6),
    requestSubRole7          (7),
    requestSubRole8          (8),
    requestSubRole9          (9),
    requestSubRole10        (10),
    requestSubRole11        (11),
    requestSubRole12        (12),
    requestSubRole13        (13),
    requestSubRole14        (14), -- The last type of sub role
    requestSubRoleReserved  (15)  -- Reserved for future use
    }
 
 
 
-- DE_ResponseType (Desc Name) Record 146
ResponseType ::= ENUMERATED {
   notInUseOrNotEquipped      (0),            
   emergency                  (1),  -- active service call at emergency level           
   nonEmergency               (2),  -- also used when returning from service call          
   pursuit                    (3),  -- sender driving may be erratic 
   stationary                 (4),  -- sender is not moving, stopped along roadside
   slowMoving                 (5),  -- such a mowers, litter trucks, etc.
   stopAndGoMovement          (6),  -- such as school bus or garbage truck   
   -- all others for Future Use
   ...
   } 
   -- values to 127 reserved for std use
   -- values 128 to 255 reserved for local use
 
 
 
-- DE_RestrictionAppliesTo (Desc Name) Record 147
RestrictionAppliesTo ::= ENUMERATED {
    none,              -- applies to nothing
    equippedTransit,   -- buses etc.
    equippedTaxis,
    equippedOther,     -- other vehicle types with
                       -- necessary signal phase state
                       -- reception equipment
    emissionCompliant, -- regional variants with more
                       -- definitive items also exist
    equippedBicycle,
    weightCompliant,
    heightCompliant,
    -- Items dealing with traveler needs
    -- (presumed to be suitably equipped)
    pedestrians,
    slowMovingPersons,
    wheelchairUsers,
    visualDisabilities,
    audioDisabilities,  -- hearing
    otherUnknownDisabilities,
    ...
    }
 
 
 
-- DE_RestrictionClassID (Desc Name) Record 148
RestrictionClassID ::= INTEGER (0..255)
   -- An index value to identify data about classes of users
   -- the value used varies with each intersection's
   -- needs and is defined in the map to the assigned 
   -- classes of supported users.
 
 
 
-- DE_RoadRegulatorID (Desc Name) Record 149
RoadRegulatorID ::= INTEGER (0..65535)
   -- The value zero shall be used for testing only
 
 
 
-- DE_RoadSegmentID (Desc Name) Record 150
RoadSegmentID ::= INTEGER (0..65535)
   -- The values zero to 255 shall be used for testing only
   -- Note that the value assign to an RoadSegment will be
   -- unique within a given regional ID only during its use
 
 
 
-- DE_RoadwayCrownAngle (Desc Name) Record 151
RoadwayCrownAngle ::= INTEGER (-128..127) 
    -- In LSB units of 0.3 degrees of angle
    -- over a range of -38.1 to + 38.1 degrees
    -- The value -128 shall be used for unknown
    -- The value zero shall be used for angles 
    -- which are between -0.15 and +0.15
 
 
 
-- DE_RTCMmessage (Desc Name) Record 152
RTCMmessage ::= OCTET STRING (SIZE(1..1023))
 
 
 
-- DE_RTCM_Revision (Desc Name) Record 153
RTCM-Revision ::= ENUMERATED {
     unknown       (0), 
     rtcmRev2      (1), -- Std 10402.x et al
     rtcmRev3      (2), -- Std 10403.x et al
     reserved      (3),
     ...  
     }
 
 
 
-- DE_Scale_B12 (Desc Name) Record 154
Scale-B12 ::= INTEGER (-2048..2047)  -- in steps of 0.05 percent
 
 
 
-- DE_SecondOfTime (Desc Name) Record 155
SecondOfTime ::= INTEGER (0..61)  -- units of seconds
    -- The value 60 shall be used for leap seconds
    -- or to indicate a full minute.
    -- The value 61 indicates that the value is unavailable
 
 
 
-- DE_SegmentAttributeLL (Desc Name) Record 156
SegmentAttributeLL ::= ENUMERATED { 
   -- Various values which can be Enabled and Disabled for a lane segement
   
   -- General Items
   reserved                  ,  
   doNotBlock                ,  -- segment where a vehicle 
                                -- may not come to a stop
   whiteLine                 ,  -- segment where lane crossing not allowed
                                -- such as the final few meters of a lane
   
   -- Porous Lane states, merging, turn outs, parking etc.
   
   mergingLaneLeft           ,  -- indicates porous lanes
   mergingLaneRight          ,
   
   curbOnLeft                ,  -- indicates presence of curbs
   curbOnRight               ,
   
   loadingzoneOnLeft         ,  -- loading or drop off zones
   loadingzoneOnRight        ,
   
   turnOutPointOnLeft        ,  -- opening to adjacent street/alley/road
   turnOutPointOnRight       ,
   
   adjacentParkingOnLeft     , -- side of road parking
   adjacentParkingOnRight    ,
   
   -- Bike Lane Needs
   adjacentBikeLaneOnLeft    , -- presence of marked bike lanes
   adjacentBikeLaneOnRight   ,
   sharedBikeLane            , -- right of way is shared with bikes
                               -- who may occupy entire lane width
   bikeBoxInFront            ,
   
   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley 
                               -- not used for crossing tracks
  
     
   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb 
                               -- but at least 1 meter remains open for use
                               -- and at-grade passage
   
   -- Lane geometry details  (see standard for defined shapes)
   taperToLeft               , -- Used to control final path shape
   taperToRight              , -- Used to control final path shape
   taperToCenterLine         , -- Used to control final path shape

   -- Parking Lane and Curb Attributes
   parallelParking           , -- 
   headInParking             , -- Parking at an angle with the street
   freeParking               , -- no restriction on use of parking
   timeRestrictionsOnParking , -- Parking is not permitted at all times
                               -- typically used when the 'parking' lane 
                               -- becomes a driving lane at times
   costToPark                , -- Used parking has a cost
   midBlockCurbPresent       , -- a protruding curb near lane edge
   unEvenPavementPresent     , -- a disjoint height at lane edge
   ...
   }
 
 
 
-- DE_SegmentAttributeXY (Desc Name) Record 157
SegmentAttributeXY ::= ENUMERATED {
   -- Various values which can be Enabled and Disabled for a lane segement
   
   -- General Items
   reserved                  ,  
   doNotBlock                ,  -- segment where a vehicle 
                                -- may not come to a stop
   whiteLine                 ,  -- segment where lane crossing not allowed
                                -- such as the final few meters of a lane
   
   -- Porous Lane states, merging, turn outs, parking etc.
   
   mergingLaneLeft           ,  -- indicates porous lanes
   mergingLaneRight          ,
   
   curbOnLeft                ,  -- indicates presence of curbs
   curbOnRight               ,
   
   loadingzoneOnLeft         ,  -- loading or drop off zones
   loadingzoneOnRight        ,
   
   turnOutPointOnLeft        ,  -- opening to adjacent street/alley/road
   turnOutPointOnRight       ,
   
   adjacentParkingOnLeft     , -- side of road parking
   adjacentParkingOnRight    ,
   
   -- Bike Lane Needs
   adjacentBikeLaneOnLeft    , -- presence of marked bike lanes
   adjacentBikeLaneOnRight   ,
   sharedBikeLane            , -- right of way is shared with bikes
                               -- who may occupy entire lane width
   bikeBoxInFront            ,
   
   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley 
                               -- not used for crossing tracks
  
     
   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb 
                               -- but at least 1 meter remains open for use
                               -- and at-grade passage
   
   -- Lane geometry details  (see standard for defined shapes)
   taperToLeft               , -- Used to control final path shape
   taperToRight              , -- Used to control final path shape
   taperToCenterLine         , -- Used to control final path shape

   -- Parking Lane and Curb Attributes
   parallelParking           , -- 
   headInParking             , -- Parking at an angle with the street
   freeParking               , -- no restriction on use of parking
   timeRestrictionsOnParking , -- Parking is not permitted at all times
                               -- typically used when the 'parking' lane 
                               -- becomes a driving lane at times
   costToPark                , -- Used parking has a cost
   midBlockCurbPresent       , -- a protruding curb near lane edge
   unEvenPavementPresent     , -- a disjoint height at lane edge
   ...
   }
 
 
 
-- DE_SemiMajorAxisAccuracy (Desc Name) Record 158
SemiMajorAxisAccuracy ::= INTEGER (0..255)
   -- semi-major accuracy at one standard dev 
   -- range 0-12.7 meter, LSB = .05m
   -- 254 = any value equal or greater than 12.70 meter
   -- 255 = unavailable semi-major value
 
 
 
-- DE_SemiMajorAxisOrientation (Desc Name) Record 159
SemiMajorAxisOrientation ::= INTEGER (0..65535)
   -- orientation of semi-major axis 
   -- relative to true north (0~359.9945078786 degrees)
   -- LSB units of 360/65535 deg  = 0.0054932479
   -- a value of 0 shall be 0 degrees
   -- a value of 1 shall be 0.0054932479 degrees 
   -- a value of 65534 shall be 359.9945078786 deg
   -- a value of 65535 shall be used for orientation unavailable
 
 
 
-- DE_SemiMinorAxisAccuracy (Desc Name) Record 160
SemiMinorAxisAccuracy ::= INTEGER (0..255)
   -- semi-minor accuracy at one standard dev 
   -- range 0-12.7 meter, LSB = .05m
   -- 254 = any value equal or greater than 12.70 meter
   -- 255 = unavailable semi-minor value
 
 
 
-- DE_SignalControlState (Desc Name) Record 161
SignalControlState ::= OCTET STRING (SIZE(1)) 
-- update to use proper current NTRIP in UPER format, ask DaveB to assit/review

    -- With bits set as follows:
   
    -- Bit 7 (MSB) Set if the state is currently active
    -- only one active state can exist at a time, and 
    -- this state should be sent first in any sequences
   
    -- Bits 6~4 The preempt or priority value that is 
    -- being described.  
   
    -- Bits 3~0 the state bits, indicating either a 
    -- preemption or a priority use as follows: 
   
    -- If a preemption: to follow the 
    -- preemptState object of NTCIP 1202 v2.19f  
    -- See PreemptState for bit definitions.
   
    -- If a prioirty to follow the 
    -- tspInputStatus object utilized in the 
    -- NYC ASTC2 traffic controller
    -- See PriorityState for bit definitions
 
 
 
-- DE_SignalGroupID (Desc Name) Record 162
SignalGroupID ::= INTEGER (0..255) 
    -- The value 0 shall be used when the ID is
    -- not available or not known
    -- the value 255 is reserved to indicate a 
    -- permanent green movement state
    -- therefore a simple 8 phase signal controller 
    -- device might use 1..9 as its groupIDs
 
 
 
-- DE_SignalReqScheme (Desc Name) Record 163
SignalReqScheme ::= OCTET STRING (SIZE(1)) 
    -- Encoded as follows: 
   -- upper nibble:  Preempt #:  
    -- Bit 7 (MSB) 1 =  Preempt and 0 =  Priority 
    -- Remaining 3 bits: 
    -- Range of 0..7. The values of 1..6 represent 
    -- the respective controller preempt or Priority 
    -- to be activated. The value of 7 represents a 
    -- request for a cabinet flash prempt, 
    -- while the value of 0 is reserved.  
   
   -- lower nibble:  Strategy #:  
    -- Range is 0..15 and is used to specify a desired 
    -- strategy (if available).  
    -- Currently no strategies are defined and this 
    -- should be zero.
 
 
 
-- DE_SignPrority (Desc Name) Record 164
SignPrority ::= INTEGER (0..7)
   -- 0 as least, 7 as most
 
 
 
-- DE_SirenInUse (Desc Name) Record 165
SirenInUse ::= ENUMERATED {
     unavailable   (0), -- Not Equipped or unavailable
     notInUse      (1),  
     inUse         (2),  
     reserved      (3)  -- for future use
     }
 
 
 
-- DE_Speed (Desc Name) Record 166
Speed ::= INTEGER (0..8191) -- Units of 0.02 m/s
          -- The value 8191 indicates that 
          -- speed is unavailable
 
 
 
-- DE_SpeedAdvice (Desc Name) Record 167
SpeedAdvice ::= INTEGER (0..500) 
    -- LSB units are 0.1 m/s^2
    -- the value 499 shall be used for values at or greater than 49.9 m/s
    -- the value 500 shall be used to indicates that speed is unavailable
 
 
 
-- DE_SpeedConfidence (Desc Name) Record 168
SpeedConfidence ::= ENUMERATED {
   unavailable (0), -- Not Equipped or unavailable
   prec100ms   (1), -- 100  meters / sec
   prec10ms    (2), -- 10   meters / sec
   prec5ms     (3), -- 5    meters / sec
   prec1ms     (4), -- 1    meters / sec
   prec0-1ms   (5), -- 0.1  meters / sec
   prec0-05ms  (6), -- 0.05 meters / sec
   prec0-01ms  (7)  -- 0.01 meters / sec
   }
 
 
 
-- DE_SpeedLimitType (Desc Name) Record 169
SpeedLimitType ::= ENUMERATED {
    unknown,                    -- Speed limit type not available
    maxSpeedInSchoolZone,       -- Only sent when the limit is active
    maxSpeedInSchoolZoneWhenChildrenArePresent, -- Sent at any time
    maxSpeedInConstructionZone, -- Used for work zones, incident zones, etc.
                                -- where a reduced speed is present
    vehicleMinSpeed,
    vehicleMaxSpeed,            -- Regulatory speed limit for general traffic
    vehicleNightMaxSpeed,

    truckMinSpeed,
    truckMaxSpeed,
    truckNightMaxSpeed,

    vehiclesWithTrailersMinSpeed,
    vehiclesWithTrailersMaxSpeed,
    vehiclesWithTrailersNightMaxSpeed,
    ...
    }
 
 
 
-- DE_SpeedProfileMeasurement (Desc Name) Record 170
SpeedProfileMeasurement ::= GrossSpeed 
 
 
 
-- DE_SSPindex (Desc Name) Record 171
SSPindex ::= INTEGER (0..31)
   -- Text here
 
 
 
-- DE_StabilityControlStatus (Desc Name) Record 172
StabilityControlStatus ::= ENUMERATED {
   unavailable (0), -- B'00  Not Equipped with SC
                    --       or SC status is unavailable
   off         (1), -- B'01  Off
   on          (2), -- B'10  On or active (but not engaged)
   engaged     (3)  -- B'11  stability control is Engaged 
   }
 
 
 
-- DE_StationID (Desc Name) Record 173
StationID ::= INTEGER (0..4294967295)
 
 
 
-- DE_J1939-71-Steering Axle Lube Pressure (Desc Name) Record 174
SteeringAxleLubePressure ::= INTEGER (0..255)
 
 
 
-- DE_J1939-71-Steering Axle Temperature (Desc Name) Record 175
SteeringAxleTemperature ::= INTEGER (0..255)
 
 
 
-- DE_SteeringWheelAngle (Desc Name) Record 176
SteeringWheelAngle ::= INTEGER (-126..127) 
    -- LSB units of 1.5 degrees, a range of -189 to +189 degrees
    -- +001 = +1.5 deg
    -- -126 = -189 deg and beyond  
    -- +126 = +189 deg and beyond
    -- +127 to be used for unavailable
 
 
 
-- DE_SteeringWheelAngleConfidence (Desc Name) Record 177
SteeringWheelAngleConfidence ::= ENUMERATED {
   unavailable (0), -- B'00  Not Equipped with Wheel angle
                    -- or Wheel angle status is unavailable
   prec2deg    (1), -- B'01  2 degrees
   prec1deg    (2), -- B'10  1 degree
   prec0-02deg (3)  -- B'11  0.02 degrees
   }
 
 
 
-- DE_SteeringWheelAngleRateOfChange (Desc Name) Record 178
SteeringWheelAngleRateOfChange ::= INTEGER (-127..127) 
   -- LSB is 3 degrees per second
 
 
 
-- DE_SunSensor (Desc Name) Record 179
SunSensor ::= INTEGER (0..1000) 
   -- units of watts / m2
 
 
 
-- DE_TemporaryID (Desc Name) Record 180
TemporaryID ::= OCTET STRING (SIZE(4))
 
 
 
-- DE_TerminationDistance (Desc Name) Record 181
TermDistance ::= INTEGER (1..30000)   -- units in meters
 
 
 
-- DE_TerminationTime (Desc Name) Record 182
TermTime ::= INTEGER (1..1800) -- units of sec
 
 
 
-- DE_ThrottleConfidence (Desc Name) Record 183
ThrottleConfidence ::= ENUMERATED {
   unavailable     (0), -- B'00  Not Equipped or unavailable
   prec10percent   (1), -- B'01  10  percent Confidence level
   prec1percent    (2), -- B'10  1   percent Confidence level
   prec0-5percent  (3)  -- B'11  0.5 percent Confidence level
   }
 
 
 
-- DE_ThrottlePosition (Desc Name) Record 184
ThrottlePosition ::= INTEGER (0..200) -- LSB units are 0.5 percent
 
 
 
-- DE_TimeConfidence (Desc Name) Record 185
TimeConfidence ::= ENUMERATED {
   unavailable              (0), -- Not Equipped or unavailable
   time-100-000             (1), -- Better then  100 Seconds
   time-050-000             (2), -- Better then  50 Seconds
   time-020-000             (3), -- Better then  20 Seconds
   time-010-000             (4), -- Better then  10 Seconds
   time-002-000             (5), -- Better then  2 Seconds
   time-001-000             (6), -- Better then  1 Second
   time-000-500             (7), -- Better then  0.5 Seconds
   time-000-200             (8), -- Better then  0.2 Seconds
   time-000-100             (9), -- Better then  0.1 Seconds
   time-000-050            (10), -- Better then  0.05 Seconds
   time-000-020            (11), -- Better then  0.02 Seconds
   time-000-010            (12), -- Better then  0.01 Seconds
   time-000-005            (13), -- Better then  0.005 Seconds
   time-000-002            (14), -- Better then  0.002 Seconds
   time-000-001            (15), -- Better then  0.001 Seconds
                                 -- Better then one milisecond
   time-000-000-5          (16), -- Better then  0.000,5 Seconds
   time-000-000-2          (17), -- Better then  0.000,2 Seconds
   time-000-000-1          (18), -- Better then  0.000,1 Seconds
   time-000-000-05         (19), -- Better then  0.000,05 Seconds
   time-000-000-02         (20), -- Better then  0.000,02 Seconds
   time-000-000-01         (21), -- Better then  0.000,01 Seconds
   time-000-000-005        (22), -- Better then  0.000,005 Seconds
   time-000-000-002        (23), -- Better then  0.000,002 Seconds
   time-000-000-001        (24), -- Better then  0.000,001 Seconds 
                                 -- Better then one micro second
   time-000-000-000-5      (25), -- Better then  0.000,000,5 Seconds
   time-000-000-000-2      (26), -- Better then  0.000,000,2 Seconds
   time-000-000-000-1      (27), -- Better then  0.000,000,1 Seconds
   time-000-000-000-05     (28), -- Better then  0.000,000,05 Seconds
   time-000-000-000-02     (29), -- Better then  0.000,000,02 Seconds
   time-000-000-000-01     (30), -- Better then  0.000,000,01 Seconds
   time-000-000-000-005    (31), -- Better then  0.000,000,005 Seconds
   time-000-000-000-002    (32), -- Better then  0.000,000,002 Seconds
   time-000-000-000-001    (33), -- Better then  0.000,000,001 Seconds
                                 -- Better then one nano second
   time-000-000-000-000-5  (34), -- Better then  0.000,000,000,5 Seconds
   time-000-000-000-000-2  (35), -- Better then  0.000,000,000,2 Seconds
   time-000-000-000-000-1  (36), -- Better then  0.000,000,000,1 Seconds
   time-000-000-000-000-05 (37), -- Better then  0.000,000,000,05 Seconds
   time-000-000-000-000-02 (38), -- Better then  0.000,000,000,02 Seconds
   time-000-000-000-000-01 (39)  -- Better then  0.000,000,000,01 Seconds 
   }
 
 
 
-- DE_TimeIntervalConfidence (Desc Name) Record 186
TimeIntervalConfidence ::= INTEGER (0..15)   
   -- Value   Probability
   --   0         21%
   --   1         36%
   --   2         47%
   --   3         56%
   --   4         62%
   --   5         68%
   --   6         73%
   --   7         77%
   --   8         81%
   --   9         85%
   --   10        88%
   --   11        91%
   --   12        94%
   --   13        96%
   --   14        98%
   --   15        100%
 
 
 
-- DE_TimeMark (Desc Name) Record 187
TimeMark ::= INTEGER (0..36002)
   -- Tenths of a second in the current or next hour
   -- In units of 1/10th second from UTC time
   -- A range of 0~36000 covers one hour
   -- The values 35991..36000 are used when a leap second occurs
   -- The value 36001 is used to indicate time >3600 seconds
   -- 36002 is to be used when value undefined or unknown
   -- Note that this is NOT expressed in GPS time
   -- or in local time
 
 
 
-- DE_TimeOffset (Desc Name) Record 188
TimeOffset ::= INTEGER (1..65535)
   -- LSB units of of 10 mSec, 
   -- with a range of 0.01 seconds to 10 minutes and 55.34 seconds
   -- a value of 65534 to be used for 655.34 seconds or greater
   -- a value of 65535 to be unavailable
 
 
 
-- DE_J1939-71-Tire Leakage Rate (Desc Name) Record 189
TireLeakageRate ::= INTEGER (0..65535)
 
 
 
-- DE_J1939-71-Tire Location (Desc Name) Record 190
TireLocation ::= INTEGER (0..255)
 
 
 
-- DE_J1939-71-Tire Pressure (Desc Name) Record 191
TirePressure ::= INTEGER (0..1000)
 
 
 
-- DE_J1939-71-Tire Pressure Threshold Detection (Desc Name) Record 192
TirePressureThresholdDetection ::= ENUMERATED {
   noData                (0),  -- B'000'
   overPressure          (1),  -- B'001' 
   noWarningPressure     (2),  -- B'010'
   underPressure         (3),  -- B'011'
   extremeUnderPressure  (4),  -- B'100'
   undefined             (5),  -- B'101'
   errorIndicator        (6),  -- B'110'
   notAvailable          (7)   -- B'111'
   }  -- Encoded as a 3 bit value
 
 
 
-- DE_J1939-71-Tire Temp (Desc Name) Record 193
TireTemp ::= INTEGER (0..65535)
 
 
 
-- DE_TractionControlStatus (Desc Name) Record 194
TractionControlStatus ::= ENUMERATED {
   unavailable (0), -- B'00  Not Equipped with traction control 
                    --       or traction control status is unavailable
   off         (1), -- B'01  traction control is Off
   on          (2), -- B'10  traction control is On (but not Engaged)
   engaged     (3)  -- B'11  traction control is Engaged
   }
 
 
 
-- DE_TrailerMass (Desc Name) Record 195
TrailerMass ::= INTEGER (0..255) 
   -- object mass with LSB steps of 500 Kg (~227 lbs)
   -- the value zero shall be uaed for an unknown mass value
   -- the value 255 shall be used any mass larger than 127,500kg
   -- a useful range of 0~127,500 metric tons. (~140.54 US short tons)
 
 
 
-- DE_J1939-71-Trailer Weight (Desc Name) Record 196
TrailerWeight ::= INTEGER (0..65535)
 
 
 
-- DE_TransitStatus (Desc Name) Record 197
TransitStatus ::= BIT STRING {
    none        (0), -- nothing is active
    anADAuse    (1), -- an ADA access is in progress (wheelchairs, kneling, etc.)
    aBikeLoad   (2), -- loading of a bicyle is in progress
    doorOpen    (3), -- a vehicle door is open for passenger access
    occM        (4),
    occL        (5)
    -- bits four and five are used to relate the 
    -- the relative occupancy of the vehicle, with
    -- 00  as least full and 11 indicating a 
    -- close-to or full conditon
    } (SIZE(6))
 
 
 
-- DE_TransitVehicleOccupancy (Desc Name) Record 198
TransitVehicleOccupancy ::= ENUMERATED {
    occupancyUnknown    (0),  
    occupancyEmpty      (1),  
    occupancyVeryLow    (2),  
    occupancyLow        (3),  
    occupancyMed        (4),  
    occupancyHigh       (5),  
    occupancyNearlyFull (6),  
    occupancyFull       (7)
    }
 
 
 
-- DE_TransitVehicleStatus (Desc Name) Record 199
TransitVehicleStatus ::= BIT STRING {
    loading     (0), -- parking and unable to move at this time
    anADAuse    (1), -- an ADA access is in progress (wheelchairs, kneeling, etc.)
    aBikeLoad   (2), -- loading of a bicycle is in progress
    doorOpen    (3), -- a vehicle door is open for passenger access
    charging    (4), -- a vehicle is connected to charging point
    atStopLine  (5)  -- a vehicle is at the stop line for the lane it is in
    } (SIZE(8))
 
 
 
-- DE_TransmissionState (Desc Name) Record 200
TransmissionState ::= ENUMERATED {
   neutral      (0), -- Neutral, speed relative to the vehicle alignment
   park         (1), -- Park, speed relative the to vehicle alignment
   forwardGears (2), -- Forward gears, speed relative the to vehicle alignment
   reverseGears (3), -- Reverse gears, speed relative the to vehicle alignment 
   reserved1    (4),      
   reserved2    (5),      
   reserved3    (6),      
   unavailable  (7)  -- not-equipped or unavailable value,
                     -- speed relative to the vehicle alignment
   }
 
 
 
-- DE_TravelerInfoType (Desc Name) Record 201
TravelerInfoType ::= ENUMERATED {
     unknown            (0), 
     advisory           (1),
     roadSignage        (2), 
     commercialSignage  (3),
     ...  
     } 
     -- values to 127 reserved for std use
     -- values 128 to 255 reserved for local use
 
 
 
-- DE_UniqueMSG_ID (Desc Name) Record 202
UniqueMSGID ::= OCTET STRING (SIZE(9))
 
 
 
-- DE_URL_Base (Desc Name) Record 203
URL-Base ::= IA5String (SIZE(1..45))
 
 
 
-- DE_URL_Link (Desc Name) Record 204
URL-Link ::= IA5String (SIZE(1..255))
 
 
 
-- DE_URL_Short (Desc Name) Record 205
URL-Short ::= IA5String (SIZE(1..15))
 
 
 
-- DE_VehicleEventFlags (Desc Name) Record 206
VehicleEventFlags ::= BIT STRING {
   eventHazardLights               (0),
   eventStopLineViolation          (1), -- Intersection Violation   
   eventABSactivated               (2),
   eventTractionControlLoss        (3),
   eventStabilityControlactivated  (4),
   eventHazardousMaterials         (5),
   eventReserved1                  (6),   
   eventHardBraking                (7),
   eventLightsChanged              (8),
   eventWipersChanged              (9),
   eventFlatTire                   (10),
   eventDisabledVehicle            (11),
   eventAirBagDeployment           (12)
   } (SIZE (13, ...))
 
 
 
-- DE_VehicleHeight (Desc Name) Record 207
VehicleHeight ::= INTEGER (0..127) 
    -- the height of the vehicle
    -- LSB units of 5 cm, range to 6.35 meters
 
 
 
-- DE_VehicleLength (Desc Name) Record 208
VehicleLength ::= INTEGER (0..16383) -- LSB units are 1 cm with a range of >163 meters

-- ISSUE To resolve in July,  
-- This at least twice as long as it needs to be.
-- Recomend use (0..4095), allows >40 meters, >131 feet
 
 
 
-- DE_VehicleMass (Desc Name) Record 209
VehicleMass ::= INTEGER (1..127) -- mass with an LSB of 50 Kg
 
 
 
-- DE_VehicleStatusDeviceTypeTag (Desc Name) Record 210
VehicleStatusDeviceTypeTag ::= ENUMERATED {
   unknown            (0),
   lights             (1),  -- Exterior Lights
   wipers             (2),  -- Wipers
   brakes             (3),  -- Brake Applied                
   stab               (4),  -- Stability Control        
   trac               (5),  -- Traction Control        
   abs                (6),  -- Anti-Lock Brakes        
   sunS               (7),  -- Sun Sensor        
   rainS              (8),  -- Rain Sensor        
   airTemp            (9),  -- Air Temperature    
   steering           (10),
   vertAccelThres     (11), -- Wheel that Exceeded the
   vertAccel          (12), -- Vertical g Force Value  
   hozAccelLong       (13), -- Longitudinal Acceleration        
   hozAccelLat        (14), -- Lateral Acceleration        
   hozAccelCon        (15), -- Acceleration Confidence 
   accel4way          (16),
   confidenceSet      (17),
   obDist             (18), -- Obstacle Distance        
   obDirect           (19), -- Obstacle Direction        
   yaw                (20), -- Yaw Rate        
   yawRateCon         (21), -- Yaw Rate Confidence
   dateTime           (22), -- complete time
   fullPos            (23), -- complete set of time and
                            -- position, speed, heading
   position2D         (24), -- lat, long
   position3D         (25), -- lat, long, elevation
   vehicle            (26), -- height, mass, type
   speedHeadC         (27), 
   speedC             (28),
   
   ...  
   }
   -- values to 127 reserved for std use
   -- values 128 to 255 reserved for local use
 
 
 
-- DE_VehicleType (Desc Name) Record 211
VehicleType ::= ENUMERATED {
   none                 (0),  -- Not Equipped, Not known or unavailable
   unknown              (1),  -- Does not fit any other category    
   special              (2),  -- Special use    
   moto                 (3),  -- Motorcycle    
   car                  (4),  -- Passenger car    
   carOther             (5),  -- Four tire single units    
   bus                  (6),  -- Buses    
   axleCnt2             (7),  -- Two axle, six tire single units    
   axleCnt3             (8),  -- Three axle, single units    
   axleCnt4             (9),  -- Four or more axle, single unit    
   axleCnt4Trailer      (10), -- Four or less axle, single trailer    
   axleCnt5Trailer      (11), -- Five or less axle, single trailer    
   axleCnt6Trailer      (12), -- Six or more axle, single trailer    
   axleCnt5MultiTrailer (13), -- Five or less axle, multi-trailer    
   axleCnt6MultiTrailer (14), -- Six axle, multi-trailer    
   axleCnt7MultiTrailer (15),  -- Seven or more axle, multi-trailer    
   ...  
   } 
   -- values to 127 reserved for std use
   -- values 128 to 255 reserved for local use
 
 
 
-- DE_VehicleWidth (Desc Name) Record 212
VehicleWidth ::= INTEGER (0..1023) -- LSB units are 1 cm with a range of >10 meters
 
 
 
-- DE_Velocity (Desc Name) Record 213
Velocity ::= INTEGER (0..8191) -- Units of 0.02 m/s
    -- The value 8191 indicates that 
    -- velocity is unavailable
 
 
 
-- DE_VerticalAcceleration (Desc Name) Record 214
VerticalAcceleration ::= INTEGER (-127..127) 
   -- LSB units of 0.02 G steps over 
   -- a range +1.54 to -3.4G 
   -- and offset by 50  Value 50 = 0g, Value 0 = -1G
   -- value +127 = 1.54G, 
   -- value -120 = -3.4G
   -- value -121 for ranges -3.4 to -4.4G
   -- value -122 for ranges -4.4 to -5.4G
   -- value -123 for ranges -5.4 to -6.4G
   -- value -124 for ranges -6.4 to -7.4G
   -- value -125 for ranges -7.4 to -8.4G
   -- value -126 for ranges larger than -8.4G
   -- value -127 for unavailable data
 
 
 
-- DE_VerticalAccelerationThreshold (Desc Name) Record 215
VerticalAccelerationThreshold ::= BIT STRING {
   allOff      (0), -- B'0000  The condition All Off or not equipped
   leftFront   (1), -- B'0001  Left Front Event
   leftRear    (2), -- B'0010  Left Rear Event
   rightFront  (4), -- B'0100  Right Front Event
   rightRear   (8)  -- B'1000  Right Rear Event
   } -- to fit in 4 bits
 
 
 
-- DE_VertOffset-B07 (Desc Name) Record 216
VertOffset-B07 ::= INTEGER (-64..63)  
   -- LSB units of of 10 cm
   -- with a range of +- 6.3 meters vertical 
   -- value  63 to be used for  63 or greater
   -- value -63 to be used for -63 or greater
   -- value -64 to be unavailablers
 
 
 
-- DE_VertOffset-B08 (Desc Name) Record 217
VertOffset-B08 ::= INTEGER (-128..127)  
   -- LSB units of of 10 cm
   -- with a range of +- 12.7 meters vertical
   -- value  127 to be used for  127 or greater
   -- value -127 to be used for -127 or greater
   -- value -128 to be unavailable
 
 
 
-- DE_VertOffset-B09 (Desc Name) Record 218
VertOffset-B09 ::= INTEGER (-256..255)  
   -- LSB units of of 10 cm
   -- with a range of +- 25.5 meters vertical
   -- value  255 to be used for  255 or greater
   -- value -255 to be used for -255 or greater
   -- value -256 to be unavailable
 
 
 
-- DE_VertOffset-B10 (Desc Name) Record 219
VertOffset-B10 ::= INTEGER (-512..511)  
   -- LSB units of of 10 cm
   -- with a range of +- 51.1 meters vertical
   -- value  511 to be used for  511 or greater
   -- value -511 to be used for -511 or greater
   -- value -512 to be unavailable
 
 
 
-- DE_VertOffset-B11 (Desc Name) Record 220
VertOffset-B11 ::= INTEGER (-1024..1023)  
   -- LSB units of of 10 cm
   -- with a range of +- 102.3 meters vertical
   -- value  1023 to be used for  1023 or greater
   -- value -1023 to be used for -1023 or greater
   -- value -1024 to be unavailable
 
 
 
-- DE_VertOffset-B12 (Desc Name) Record 221
VertOffset-B12 ::= INTEGER (-2048..2047)  
   -- LSB units of of 10 cm
   -- with a range of +- 204.7 meters vertical
   -- value  2047 to be used for  2047 or greater
   -- value -2047 to be used for -2047 or greater
   -- value -2048 to be unavailable
 
 
 
-- DE_VINstring, (Desc Name) Record 222
VINstring ::= OCTET STRING (SIZE(1..17)) 
   -- A legal VIN or a shorter value 
   -- to provide an ident of the vehicle
   -- If a VIN is sent, then IA5 encoding 
   -- shall be used
 
 
 
-- DE_WaitOnStopline (Desc Name) Record 223
WaitOnStopline ::= BOOLEAN -- 
         -- True or False
         -- If "true", the vehicles on this specific connecting 
         -- maneuver have to stop on the stop-line
         -- and not to enter the collision area
 
 
 
-- DE_J1939-71-Wheel End Elect. Fault (Desc Name) Record 224
WheelEndElectFault ::= BIT STRING {
   bitOne      (0),
   bitTwo      (1),
   bitThree    (2),
   bitFour     (3)
   } (SIZE (4))
 
 
 
-- DE_J1939-71-Wheel Sensor Status (Desc Name) Record 225
WheelSensorStatus ::= ENUMERATED {
   off           (0), 
   on            (1),
   notDefined    (2), 
   notSupported  (3)
   }  -- Encoded as a 2 bit value
 
 
 
-- DE_WiperRate (Desc Name) Record 226
WiperRate ::= INTEGER (0..127) -- units of sweeps per minute
 
 
 
-- DE_WiperStatus (Desc Name) Record 227
WiperStatus ::= ENUMERATED {
     unavailable         (0), -- Not Equipped with wiper status
                              -- or wiper status is unavailable
     off                 (1),  
     intermittent        (2), 
     low                 (3),
     high                (4),
     washerInUse         (5), -- washing solution being used
     automaticPresent    (6), -- Auto wiper equipped
     ...  
     }
 
 
 
-- DE_YawRate (Desc Name) Record 228
YawRate ::= INTEGER (-32767..32767) 
   -- LSB units of 0.01 degrees per second (signed)
 
 
 
-- DE_YawRateConfidence (Desc Name) Record 229
YawRateConfidence ::= ENUMERATED {
   unavailable    (0), -- B'000  Not Equipped with yaw rate status
                       -- or yaw rate status is unavailable
   degSec-100-00  (1), -- B'001  100  deg/sec
   degSec-010-00  (2), -- B'010  10   deg/sec
   degSec-005-00  (3), -- B'011  5    deg/sec
   degSec-001-00  (4), -- B'100  1    deg/sec
   degSec-000-10  (5), -- B'101  0.1  deg/sec
   degSec-000-05  (6), -- B'110  0.05 deg/sec
   degSec-000-01  (7)  -- B'111  0.01 deg/sec
   }  
   -- Encoded as a 3 bit value
 
 
 
-- DE_ZoneLength (Desc Name) Record 230
ZoneLength ::= INTEGER (0..10000)
    -- Unit = 1 meter, 0 = unknown, 
    -- The value 10000 to be used for Distances >=10000 m
    -- (e.g. from known point to another point along a 
    -- known path, often against traffic flow direction 
    -- when used for measuring queues)
 
 
 
-- DE_Zoom (Desc Name) Record 231
Zoom ::= INTEGER (0..15)
   -- A zoom scale applied in units of 2^N
   -- A value of 0 is a 1:1 zoom (no zoom)
   -- A value of 1 is a 2:1 zoom
   -- A value of 2 is a 4:1 zoom, etc.
   -- The zoom value is applied to one or more offsets
   -- increase the span or range while reducing its precision
   -- The absence of a zoom, any offset element in a data 
   -- frame implies a 1:1 zoom
 
 


-- Unable to find the file: DSRCstubs.txt
-- Which would be be inserted at this point if present.


END 
-- end of the DSRC module.
 
 
 
-- -_-_-_-_-_-_-_-_-_-_-_-_-_-_-_-_-_-_-_-_-_-_-_-_-_-_-_-_
-- 
-- Start of External Data entries...
-- Grouped into sets of modules
-- -_-_-_-_-_-_-_-_-_-_-_-_-_-_-_-_-_-_-_-_-_-_-_-_-_-_-_-_
-- 
-- ^-^-^-^-^-^-^-^-^-^-^-^-^-^-^-^-^-^-^-^-^-^-^-^-^-^-^-^-
-- 
-- Begin module: AddGrpC
-- 
-- ^-^-^-^-^-^-^-^-^-^-^-^-^-^-^-^-^-^-^-^-^-^-^-^-^-^-^-^-
AddGrpC DEFINITIONS AUTOMATIC TAGS::= BEGIN 
 


-- DF_Altitude_EU (Desc Name) Record 1
-- From source: ADOPTED  Regional Data J2735 (AddGrpC)
Altitude ::=  SEQUENCE {
   value        AltitudeValue,
   confidence   AltitudeConfidence
   }

-- DE_AltitudeConfidence_EU (Desc Name) Record 2
-- From source: ADOPTED  Regional Data J2735 (AddGrpC)
AltitudeConfidence ::= ENUMERATED {
   alt-000-01,  -- accuracy within    0.01 meter
   alt-000-02,  -- accuracy within    0.02 meter
   alt-000-05,  -- accuracy within    0.05 meter
   alt-000-10,  -- accuracy within    0.10 meter
   alt-000-20,  -- accuracy within    0.20 meter
   alt-000-50,  -- accuracy within    0.50 meter
   alt-001-00,  -- accuracy within    1.00 meter
   alt-002-00,  -- accuracy within    2.00 meter
   alt-005-00,  -- accuracy within    5.00 meter
   alt-010-00,  -- accuracy within   10.00 meter
   alt-020-00,  -- accuracy within   20.00 meter
   alt-050-00,  -- accuracy within   50.00 meter
   alt-100-00,  -- accuracy within  100.00 meter
   alt-200-00,  -- accuracy within  200.00 meter
   outOfRange,  -- accuracy exceeds 200.00 meters
   unavailable  -- unavailable
}

-- DE_AltitudeValue_EU (Desc Name) Record 3
-- From source: ADOPTED  Regional Data J2735 (AddGrpC)
AltitudeValue ::= INTEGER (-100000..800001)  -- units of  0.01 meter 
   -- Where: 
   -- seaLevel(0), 
   -- oneCentimeter(1), 
   -- unavailable(800001)

-- DF_REG_ConnectionManeuverAssist_EU (Desc Name) Record 5
-- From source: ADOPTED  Regional Data J2735 (AddGrpC)
ConnectionManeuverAssist-addGrpC ::=  SEQUENCE {
    vehicleToLanePositions  VehicleToLanePositionList,
    rsuDistanceFromAnchor   DSRC.NodeOffsetPointXY OPTIONAL
}

-- DE_EmissionType_EU (Desc Name) Record 11
-- From source: ADOPTED  Regional Data J2735 (AddGrpC)
EmissionType ::= ENUMERATED {
     typeA,  -- check for proper restrictions
     typeB,  -- 
     typeC,  -- 
     typeD,  -- 
     typeE,  -- 
     ...  
     }

-- DF_REG_IntersectionState_EU (Desc Name) Record 20
-- From source: ADOPTED  Regional Data J2735 (AddGrpC)
IntersectionState-addGrpC ::=  SEQUENCE { 
   activePrioritizations PrioritizationResponseList OPTIONAL,
   ... }

-- DF_REG_MapData_Base_EU (Desc Name) Record 29
-- From source: ADOPTED  Regional Data J2735 (AddGrpC)
MapData-addGrpC ::=  SEQUENCE { 
   signalHeadLocations   SignalHeadLocationList OPTIONAL,
   ... 
   }

-- DF_REG_Position3D_EU (Desc Name) Record 41
-- From source: ADOPTED  Regional Data J2735 (AddGrpC)
Position3D-addGrpC ::=  SEQUENCE {
   altitude    Altitude, 
   ...
   }

-- DF_PrioritizationResponse_EU (Desc Name) Record 42
-- From source: ADOPTED  Regional Data J2735 (AddGrpC)
PrioritizationResponse ::=  SEQUENCE {
   stationID      DSRC.StationID,
                  -- Id of requesting vehicle
                  -- Note that the stationID has to remain unchanged 
                  -- during the whole prioritisation process
   priorState     DSRC.PrioritizationResponseStatus,
                  -- State of prioritization request
   signalGroup    DSRC.SignalGroupID,
                  -- id of prioritized LaneSet, which will 
                  -- be given free way 
   ...  
   }

-- DF_PrioritizationResponseList_EU (Desc Name) Record 43
-- From source: ADOPTED  Regional Data J2735 (AddGrpC)
PrioritizationResponseList ::=  SEQUENCE SIZE(1..10) OF PrioritizationResponse

-- DF_REG_RestrictionUserType_EU (Desc Name) Record 45
-- From source: ADOPTED  Regional Data J2735 (AddGrpC)
RestrictionUserType-addGrpC ::=  SEQUENCE {
   emission   EmissionType OPTIONAL,
   ...
   }

-- DF_SignalHeadLocation_EU (Desc Name) Record 48
-- From source: ADOPTED  Regional Data J2735 (AddGrpC)
SignalHeadLocation ::=  SEQUENCE {
   node             DSRC.NodeOffsetPointXY, -- the location
   signalGroupID    DSRC.SignalGroupID,   
   ...
}

-- DF_SignalHeadLocationList_EU (Desc Name) Record 49
-- From source: ADOPTED  Regional Data J2735 (AddGrpC)
SignalHeadLocationList ::=  SEQUENCE (SIZE(1..20)) OF  SignalHeadLocation

-- DF_VehicleToLanePosition_EU (Desc Name) Record 55
-- From source: ADOPTED  Regional Data J2735 (AddGrpC)
VehicleToLanePosition ::=  SEQUENCE {
    stationID   DSRC.StationID, 
    laneID      DSRC.LaneID,
    ...  
    }

-- DF_VehicleToLanePositionList_EU (Desc Name) Record 56
-- From source: ADOPTED  Regional Data J2735 (AddGrpC)
VehicleToLanePositionList ::=  SEQUENCE SIZE(1..5) OF VehicleToLanePosition


-- Unable to find the file: AddGrpCstubs.txt
-- Which would be be inserted at this point if present.


 
END
-- End of the AddGrpC module.
 
-- ^-^-^-^-^-^-^-^-^-^-^-^-^-^-^-^-^-^-^-^-^-^-^-^-^-^-^-^-
-- 
-- Begin module: AddGrpB
-- 
-- ^-^-^-^-^-^-^-^-^-^-^-^-^-^-^-^-^-^-^-^-^-^-^-^-^-^-^-^-
AddGrpB DEFINITIONS AUTOMATIC TAGS::= BEGIN 
 


-- DE_Angle_JPN (Desc Name) Record 4
-- From source: ADOPTED  Regional Data J2735 (AddGrpB)
Angle ::= INTEGER (0..239)
   -- Unsigned units of 1.5 degree, in 1 octet
   -- the true north is 0, positive is clockwise
   -- the values 240 to 254 shall not be sent
   -- the value 255 (0xFF) indicates an invalid value

-- DE_Day_JPN (Desc Name) Record 6
-- From source: ADOPTED  Regional Data J2735 (AddGrpB)
Day ::= INTEGER (0..255) 
   -- BCD coding of Day of Month, in 1 octet
   -- values with nibble values between 1010 and 1111 shall not be sent
   -- except that the value xxx (0xFF shall indicate an invalid value

-- DE_DayOfWeek_JPN (Desc Name) Record 7
-- From source: ADOPTED  Regional Data J2735 (AddGrpB)
DayOfWeek ::= ENUMERATED {
    unknown   (0),
    monday    (1),
    tuesday   (2),
    wednesday (3),
    thursday  (4),
    friday    (5),
    saturday  (6),
    sunday    (7)
    }
   -- Encoding as per above, in 3 bits
   -- the value 0x00 shall indicate an invalid value

-- DE_DegreesLat_JPN (Desc Name) Record 8
-- From source: ADOPTED  Regional Data J2735 (AddGrpB)
DegreesLat ::= INTEGER (-90..90)
   -- Signed units of degrees, in 1 octets
   -- the values  +91 to +126 shall not be sent
   -- the values -128 to  -91 shall not be sent
   -- the value 127 (0x7F) shall indicate an invalid value

-- DE_DegreesLong_JPN (Desc Name) Record 9
-- From source: ADOPTED  Regional Data J2735 (AddGrpB)
DegreesLong ::= INTEGER (-180..180) 
   -- Signed units of degrees, in 2 octets
   -- the values +181 to +32766 shall not be sent
   -- the values -181 to -32768 shall not be sent
   -- the value 32767 (0x7FFF shall indicate an invalid value

-- DE_Elevation_JPN (Desc Name) Record 10
-- From source: ADOPTED  Regional Data J2735 (AddGrpB)
Elevation ::= INTEGER (-32768..32767)  
  -- Signed units of 0.1m (10cm), in 2 octets
  -- the value 32767 (0x7FFF) shall indicate an invalid value

-- DE_Holiday_JPN (Desc Name) Record 17
-- From source: ADOPTED  Regional Data J2735 (AddGrpB)
Holiday ::= ENUMERATED {
    weekday  (0),
    holiday  (1)
    }
   -- Encoding as per above, in 1 bit

-- DE_Hour_JPN (Desc Name) Record 18
-- From source: ADOPTED  Regional Data J2735 (AddGrpB)
Hour ::= INTEGER (0..255) 
   -- BCD coding of Hour of a Day, in 1 octet
   -- values above upper nibble 0010 and lower nibble 0100 shall not be sent
   -- values with lower nibble values between 1010 and 1111 shall not be sent
   -- except that the value 255 (0xFF) shall indicate an invalid value

-- DF_REG_LaneDataAttribute_JPN (Desc Name) Record 24
-- From source: ADOPTED  Regional Data J2735 (AddGrpB)
LaneDataAttribute-addGrpB ::=  SEQUENCE { ... }

-- DE_LatitudeDMS (Desc Name) Record 25
-- From source: ADOPTED  Regional Data J2735 (AddGrpB)
LatitudeDMS ::= INTEGER (-32400000.. 32400000) 
   -- Signed units of 0.01 seconds of a minute of a degree of Latitude
   -- Providing a range of plus-minus 90 degrees
   -- in a 4 octet value when implicit or in BER forms
   -- the value 0x7FFF FFFF shall indicate an invalid value

-- DF_LatitudeDMS2 (Desc Name) Record 26
-- From source: ADOPTED  Regional Data J2735 (AddGrpB)
LatitudeDMS2 ::=  SEQUENCE {
   d  DegreesLat,    -- units of degrees
   m  MinutesAngle,  -- units of minutes
   s  SecondsAngle   -- units of 1/100th seconds
   } -- total size of 4 octets (32 bits) when implicit encoding is used

-- DE_LongitudeDMS (Desc Name) Record 27
-- From source: ADOPTED  Regional Data J2735 (AddGrpB)
LongitudeDMS ::= INTEGER (-64800000.. 64800000) 
   -- Signed units of 0.01 seconds of a minute of a degree of Longitude
   -- Providing a range of plus-minus 180 degrees
   -- in a 4 octet value when implicit or in BER forms
   -- the value 0x7FFF FFFF shall indicate an invalid value

-- DF_LongitudeDMS2 (Desc Name) Record 28
-- From source: ADOPTED  Regional Data J2735 (AddGrpB)
LongitudeDMS2 ::=  SEQUENCE {
   d  DegreesLong,   -- units of degrees
   m  MinutesAngle,  -- units of minutes
   s  SecondsAngle   -- units of 1/100th seconds
   } -- total size of 5 octets (40 bits) when implicit encoding is used

-- DE_MaxTimetoChange (Desc Name) Record 30
-- From source: ADOPTED  Regional Data J2735 (AddGrpB)
MaxTimetoChange ::= INTEGER (0..2402)
   -- Unsigned units of 0.1 seconds, in 2 octets
   -- the value 2401 shall indicate 'forever'
   -- the values 2402 to 65534 shall not be sent
   -- the value 65535 (0xFFFF) shall indicate an invalid value

-- DE_MinTimetoChange (Desc Name) Record 31
-- From source: ADOPTED  Regional Data J2735 (AddGrpB)
MinTimetoChange ::= INTEGER (0..2402)
   -- Unsigned units of 0.1 seconds, in 2 octets
   -- the value 2401 shall indicate 'forever'
   -- the values 2402 to 32766 shall not be sent
   -- the value 32767(0x7FFF) shall indicate an invalid value
   -- Note that:
   -- The MSB is used as a flag and set to one to
   -- indicate that the value does not count down.
   -- Under this condition the movement phase may end
   -- immediately if certain condition are meet.

-- DE_Minute_JPN (Desc Name) Record 32
-- From source: ADOPTED  Regional Data J2735 (AddGrpB)
Minute ::= INTEGER (0..255) 
   -- BCD coding of Minute of an Hour, in 1 octet 
   -- values above a combined BCD value of 59 (>59)
   -- (i.e. 0110 0000) shall not be sent
   -- except that value 255 (0xFF) shall indicate an invalid value

-- DE_MinutesAngle_JPN (Desc Name) Record 33
-- From source: ADOPTED  Regional Data J2735 (AddGrpB)
MinutesAngle ::= INTEGER (0..59)   
   -- Unsigned units of minutes of an angle, in 1 octet 
   -- values above 59 shall not be sent
   -- except that value 255 (0xFF) shall indicate an invalid value

-- DE_Month_JPN (Desc Name) Record 34
-- From source: ADOPTED  Regional Data J2735 (AddGrpB)
Month ::= INTEGER (1..255) 
   -- BCD coding of Month of a year, in 1 octet
   -- values above a combined BCD value of 12 (>12)
   -- (i.e. 0001 0011) shall not be sent
   -- except that value 255 (0xFF) shall indicate an invalid value

-- DF_REG_MovementEvent_JPN (Desc Name) Record 35
-- From source: ADOPTED  Regional Data J2735 (AddGrpB)
MovementEvent-addGrpB ::=  SEQUENCE {
   -- A set of countdown style time-to-change values
   -- all in units of 0.1 seconds and following
   -- the naming of the base DSRC standard

   startTime   TimeRemaining   OPTIONAL,
               -- When this phase 1st started
   minEndTime  MinTimetoChange,
               -- Expected shortest end time
   maxEndTime  MaxTimetoChange OPTIONAL,
               -- Expected longer end time
   likelyTime  TimeRemaining   OPTIONAL,
               -- Best predicted value based on other data             
   confidence  DSRC.TimeIntervalConfidence   OPTIONAL,
               -- Applies to above time element only
   nextTime    TimeRemaining   OPTIONAL,
   ...
   }

-- DE_MsgCount_JPN (Desc Name) Record 36
-- From source: ADOPTED  Regional Data J2735 (AddGrpB)
MsgCount ::= INTEGER (0..255)
   -- a count value which is incremented with each use
   -- the next value after 255 shall be one
   -- value 0 (0x00) shall indicate that MsgCount is not available

-- DF_Node_LLdms_48b (Desc Name) Record 37
-- From source: ADOPTED  Regional Data J2735 (AddGrpB)
Node-LLdms-48b ::=  SEQUENCE {
   lon  LongitudeDMS,
   lat  LatitudeDMS
   }

-- DF_Node_LLdms_80b (Desc Name) Record 38
-- From source: ADOPTED  Regional Data J2735 (AddGrpB)
Node-LLdms-80b ::=  SEQUENCE {
   lon  LongitudeDMS2,
   lat  LatitudeDMS2
   }

-- DF_REG_NodeOffsetPointXY_JPN (Desc Name) Record 39
-- From source: ADOPTED  Regional Data J2735 (AddGrpB)
NodeOffsetPointXY-addGrpB ::=  CHOICE {
   -- Full position expressed in units of 0.01 seconds
   posA    Node-LLdms-48b,

   -- Full position expressed in multiple elements in
   -- an DD.MM.SS.sss style format
   posB    Node-LLdms-80b,

   ...
   }

-- DF_REG_Position3D_JPN (Desc Name) Record 40
-- From source: ADOPTED  Regional Data J2735 (AddGrpB)
Position3D-addGrpB ::=  SEQUENCE {
   latitude     LatitudeDMS2,
   longitude    LongitudeDMS2,
   elevation    Elevation,
   ...
   }

-- DE_Second_JPN (Desc Name) Record 46
-- From source: ADOPTED  Regional Data J2735 (AddGrpB)
Second ::= INTEGER (0..60) 
   -- BCD coding of a second of time, in 1 octet 
   -- values above a combined BCD value of 60
   -- (i.e. 0110 0000) shall not be sent
   -- except that value 255 (0xFF) shall indicate an invalid value

-- DE_SecondsAngle_JPN (Desc Name) Record 47
-- From source: ADOPTED  Regional Data J2735 (AddGrpB)
SecondsAngle ::= INTEGER (0..5999)  
   -- Unsigned units of 1/100th seconds of angle, in 2 octets
   -- values from 6000 to 65534 shall not be sent
   -- the value 65535 (0xFFFF) shall indicate an invalid value

-- DE_SummerTime_JPN (Desc Name) Record 50
-- From source: ADOPTED  Regional Data J2735 (AddGrpB)
SummerTime ::= ENUMERATED {
    notInSummerTime   (0),
    inSummerTime      (1)
    }
   -- Encoding as per above, in 1 bit

-- DE_TenthSecond_JPN (Desc Name) Record 51
-- From source: ADOPTED  Regional Data J2735 (AddGrpB)
TenthSecond ::= INTEGER (0..9) 
   -- Unsigned units of 100 milliseconds, in 1 octet
   -- values from 10 to 254 shall not be sent
   -- the value 255 (0xFF) shall indicate an invalid value

-- DF_TimeMark_JPN (Desc Name) Record 52
-- From source: ADOPTED  Regional Data J2735 (AddGrpB)
TimeMark ::=  SEQUENCE {
    year        Year,         -- BCD coding of A.D.    2 octets
    month       Month,        -- BCD coding of Month,  1 octet
    day         Day,          -- BCD coding of Day,    1 octet
    summerTime  SummerTime,
    holiday     Holiday,
    dayofWeek   DayOfWeek,
    hour        Hour,         -- BCD coding of Hour,   1 octet
    minute      Minute,       -- BCD coding of Minute, 1 octet
    second      Second,       -- BCD coding of Second, 1 octet
    tenthSecond TenthSecond   -- units of 100 millisecond, 1 octet
}

-- DE_TimeRemaining_JPN (Desc Name) Record 53
-- From source: ADOPTED  Regional Data J2735 (AddGrpB)
TimeRemaining ::= INTEGER (0..9001)
    -- Unsigned units of 0.1 seconds, spanning 15 minutes, in 2 octets
    -- the value 9001 shall indicate 'forever'
    -- values from 9002 to 65534 shall not be sent
    -- the value 65535 (0xFFFF) shall indicate an invalid value

-- DE_Year_JPN (Desc Name) Record 57
-- From source: ADOPTED  Regional Data J2735 (AddGrpB)
Year ::= INTEGER (1..65535)
   -- BCD coding of four digits of the year A.D. in 2 octets 
   -- values with nibble values between 1010 and 1111 shall not be sent
   -- except that the value 65535 (0xFFFF) shall indicate an invalid value


-- Unable to find the file: AddGrpBstubs.txt
-- Which would be be inserted at this point if present.


 
END
-- End of the AddGrpB module.
 
-- ^-^-^-^-^-^-^-^-^-^-^-^-^-^-^-^-^-^-^-^-^-^-^-^-^-^-^-^-
-- 
-- Begin module: NTCIP
-- 
-- ^-^-^-^-^-^-^-^-^-^-^-^-^-^-^-^-^-^-^-^-^-^-^-^-^-^-^-^-
NTCIP DEFINITIONS AUTOMATIC TAGS::= BEGIN 
 


-- ESS_EssMobileFriction (Desc Name) Record 12
-- From source: NTCIP 1204
EssMobileFriction ::= INTEGER (0..101)

-- ESS_EssPrecipRate_quantity (Desc Name) Record 13
-- From source: NTCIP 1204
EssPrecipRate ::= INTEGER (0..65535) 

-- ESS_EssPrecipSituation_code (Desc Name) Record 14
-- From source: NTCIP 1204
EssPrecipSituation ::= ENUMERATED {
   other (1), 
   unknown (2), 
   noPrecipitation (3), 
   unidentifiedSlight (4), 
   unidentifiedModerate (5), 
   unidentifiedHeavy (6), 
   snowSlight (7), 
   snowModerate (8), 
   snowHeavy (9), 
   rainSlight (10), 
   rainModerate (11), 
   rainHeavy (12), 
   frozenPrecipitationSlight (13), 
   frozenPrecipitationModerate (14), 
   frozenPrecipitationHeavy (15)
   }

-- ESS_EssPrecipYesNo_code (Desc Name) Record 15
-- From source: NTCIP 1204
EssPrecipYesNo ::= ENUMERATED {precip (1), noPrecip (2), error (3)} 

-- ESS_EssSolarRadiation_quantity (Desc Name) Record 16
-- From source: NTCIP 1204
EssSolarRadiation ::= INTEGER (0..65535) 


-- Unable to find the file: NTCIPstubs.txt
-- Which would be be inserted at this point if present.


 
END
-- End of the NTCIP module.
 
-- ^-^-^-^-^-^-^-^-^-^-^-^-^-^-^-^-^-^-^-^-^-^-^-^-^-^-^-^-
-- 
-- Begin module: ITIS
-- 
-- ^-^-^-^-^-^-^-^-^-^-^-^-^-^-^-^-^-^-^-^-^-^-^-^-^-^-^-^-
ITIS DEFINITIONS AUTOMATIC TAGS::= BEGIN 
 


-- DE_Incident Response Equipment (Desc Name) Record 19
-- From source: SAE ITIS Terms
IncidentResponseEquipment ::= ENUMERATED { 
   ground-fire-suppression          (9985),   
   heavy-ground-equipment           (9986),   
   aircraft                         (9988),   
   marine-equipment                 (9989),   
   support-equipment                (9990),   
   medical-rescue-unit              (9991),   
   other                            (9993),   -- Depreciated by fire standards, do not
                                              -- use
   ground-fire-suppression-other    (9994),   
   engine                           (9995),   
   truck-or-aerial                  (9996),   
   quint                            (9997),   -- A five-function type of fire 
                                              -- apparatus. The units in the 
                                              -- movie Backdraft were quints
   tanker-pumper-combination        (9998),   
   brush-truck                      (10000),  
   aircraft-rescue-firefighting     (10001),  
   heavy-ground-equipment-other     (10004),  
   dozer-or-plow                    (10005),  
   tractor                          (10006),  
   tanker-or-tender                 (10008),  
   aircraft-other                   (10024),  
   aircraft-fixed-wing-tanker       (10025),  
   helitanker                       (10026),  
   helicopter                       (10027),  
   marine-equipment-other           (10034),  
   fire-boat-with-pump              (10035),  
   boat-no-pump                     (10036),  
   support-apparatus-other          (10044),  
   breathing-apparatus-support      (10045),  
   light-and-air-unit               (10046),  
   medical-rescue-unit-other        (10054),  
   rescue-unit                      (10055),  
   urban-search-rescue-unit         (10056),  
   high-angle-rescue                (10057),  
   crash-fire-rescue                (10058),  
   bLS-unit                         (10059),  
   aLS-unit                         (10060),  
   mobile-command-post              (10075),  -- Depreciated, do not use
   chief-officer-car                (10076),  
   hAZMAT-unit                      (10077),  
   type-i-hand-crew                 (10078),  
   type-ii-hand-crew                (10079),  
   privately-owned-vehicle          (10083),  -- (Often found in volunteer fire teams)
   other-apparatus-resource         (10084),  -- (Remapped from fire code zero)
   ambulance                        (10085),  
   bomb-squad-van                   (10086),  
   combine-harvester                (10087),  
   construction-vehicle             (10088),  
   farm-tractor                     (10089),  
   grass-cutting-machines           (10090),  
   hAZMAT-containment-tow           (10091),  
   heavy-tow                        (10092),  
   light-tow                        (10094),  
   flatbed-tow                      (10114), 
   hedge-cutting-machines           (10093),  
   mobile-crane                     (10095),  
   refuse-collection-vehicle        (10096),  
   resurfacing-vehicle              (10097),  
   road-sweeper                     (10098),  
   roadside-litter-collection-crews (10099),  
   salvage-vehicle                  (10100),  
   sand-truck                       (10101),  
   snowplow                         (10102),  
   steam-roller                     (10103),  
   swat-team-van                    (10104),  
   track-laying-vehicle             (10105),  
   unknown-vehicle                  (10106),  
   white-lining-vehicle             (10107),  -- Consider using Roadwork "road marking
                                              -- operations" unless objective is to
                                              -- refer to the specific vehicle of this
                                              -- type.  Alternative Rendering: line
                                              -- painting vehicle
   dump-truck                       (10108),  
   supervisor-vehicle               (10109),  
   snow-blower                      (10110),  
   rotary-snow-blower               (10111),  
   road-grader                      (10112),  -- Alternative term: motor grader
   steam-truck                      (10113),  -- A special truck that thaws culverts 
                                              -- and storm drains
   ... -- # LOCAL_CONTENT_ITIS 
   }

-- EXT_ITIS_Codes (Desc Name) Record 21
-- From source: Adopted SAE J2540-2  (ITIS Phrases), March 2002
ITIScodes ::= INTEGER (0..65565)
-- The defined list of ITIS codes is too long to list here
-- Many smaller lists use a sub-set of these codes as defined elements
-- Also enumerated values expressed as text constant are very common,
-- and in many deployments the list codes are used as a shorthand for
-- this text.  Also the XML expressions commonly use a union of the 
-- code values and the textual expressions.  
-- Consult SAE J2540 for further details.

-- DF_ITIS-Codes_And_Text (Desc Name) Record 22
-- From source: Adopted SAE J2540-2  (ITIS Phrases), March 2002
ITIScodesAndText ::=  SEQUENCE (SIZE(1..100)) OF SEQUENCE {
  item CHOICE    {
       itis ITIScodes,
       text ITIStext
       } -- # UNTAGGED
  }

-- DE_ITIS_Text (Desc Name) Record 23
-- From source: Adopted SAE J2540-2  (ITIS Phrases), March 2002
ITIStext ::= IA5String (SIZE(1..500))

-- DE_Responder Group Affected (Desc Name) Record 44
-- From source: SAE ITIS Terms
ResponderGroupAffected ::= ENUMERATED { 
   emergency-vehicle-units           (9729),  -- Default, to be used when one of
                                              -- the below does not fit better
   federal-law-enforcement-units     (9730),  
   state-police-units                (9731),  
   county-police-units               (9732),  -- Hint: also sheriff response units
   local-police-units                (9733),  
   ambulance-units                   (9734),  
   rescue-units                      (9735),  
   fire-units                        (9736),  
   hAZMAT-units                      (9737),  
   light-tow-unit                    (9738),  
   heavy-tow-unit                    (9739),  
   freeway-service-patrols           (9740),  
   transportation-response-units     (9741),  
   private-contractor-response-units (9742),  
   ... -- # LOCAL_CONTENT_ITIS 
   }
   -- These groups are used in coordinated response and staging area information
   -- (rather than typically consumer related)

-- DE_Vehicle Groups Affected (Desc Name) Record 54
-- From source: SAE ITIS Terms
VehicleGroupAffected ::= ENUMERATED { 
   all-vehicles                               (9217),  
   bicycles                                   (9218),  
   motorcycles                                (9219),  -- to include mopeds as well
   cars                                       (9220),  -- (remapped from ERM value of
                                                       -- zero)
   light-vehicles                             (9221),  
   cars-and-light-vehicles                    (9222),  
   cars-with-trailers                         (9223),  
   cars-with-recreational-trailers            (9224),  
   vehicles-with-trailers                     (9225),  
   heavy-vehicles                             (9226),  
   trucks                                     (9227),  
   buses                                      (9228),  
   articulated-buses                          (9229),  
   school-buses                               (9230),  
   vehicles-with-semi-trailers                (9231),  
   vehicles-with-double-trailers              (9232),  -- Alternative Rendering:  
                                                       -- western doubles
   high-profile-vehicles                      (9233),  
   wide-vehicles                              (9234),  
   long-vehicles                              (9235),  
   hazardous-loads                            (9236),  
   exceptional-loads                          (9237),  
   abnormal-loads                             (9238),  
   convoys                                    (9239),  
   maintenance-vehicles                       (9240),  
   delivery-vehicles                          (9241),  
   vehicles-with-even-numbered-license-plates (9242),  
   vehicles-with-odd-numbered-license-plates  (9243),  
   vehicles-with-parking-permits              (9244),  
   vehicles-with-catalytic-converters         (9245),  
   vehicles-without-catalytic-converters      (9246),  
   gas-powered-vehicles                       (9247),  
   diesel-powered-vehicles                    (9248),  
   lPG-vehicles                               (9249),  
   military-convoys                           (9250),  
   military-vehicles                          (9251),  
   ... -- # LOCAL_CONTENT_ITIS 
   }
   -- Classification of vehicles and types of transport


-- Unable to find the file: ITISstubs.txt
-- Which would be be inserted at this point if present.


 
END
-- End of the ITIS module.
 
 
-- No entries were found with unknown module assignments.
 
 


-- Unable to find the file: ASNstubs.txt
-- Which would be be inserted at this point if present.



-- End of file output at 9/1/2015 7:29:03 PM
