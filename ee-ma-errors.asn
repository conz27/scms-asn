Ieee1609Dot2EndEntityMaError
{iso(1) identified-organization(3) ieee(111) 
standards-association-numbered-series-standards(2) wave-stds(1609)  
dot2(2) scms(2) errors(2) ee-ma (7)}

DEFINITIONS AUTOMATIC TAGS ::= BEGIN

EXPORTS ALL;

EndEntityMaError ::= ENUMERATED {
  maMalformedRequest,
  maDecryptionFailed,
  eeEncryptionFailed,
  ...
}



END
