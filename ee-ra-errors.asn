Ieee1609Dot2EndEntityRaError
{iso(1) identified-organization(3) ieee(111) 
standards-association-numbered-series-standards(2) wave-stds(1609)  
dot2(2) scms(2) errors(2) ee-ra (8)}

DEFINITIONS AUTOMATIC TAGS ::= BEGIN

EXPORTS ALL;

-- RA Triggered Error Codes

EndEntityRaError ::= CHOICE {
  obe-error                 ObeError,
  rse-error                 RseError,
  ra-soft-error             RaSoftError,
  ra-hard-error             RaHardError,
  ...
}

RaSoftError ::= ENUMERATED {
	-- Device policies out of date, soft error
	policyOutOfDate,
	...
}

RaHardError ::= ENUMERATED {
    -- EE-to-RA authentication failed
    authenticationFailed,
    -- EE tries to communicate without TLS protection
    noTLS, 
    -- EE requests invalid URL 
    requestedInvalidURL, 
    -- Device policies out of date, hard error
    policyOutOfDate, 
    -- Device enrollment certificate blacklisted, expired, unauthorized
    invalidCredentials, 
    -- Device signature invalid
    invalidSignature,
    -- Unauthorized request permissions invalid
    invalidPermissions,
    -- Malformed provisioning request
    malformedRequest,
    -- RA does not service this device
    doesNotService,
    -- Invalid device system time
    invalidSystemTime,
    -- Too many provisioning requests by device
    tooManyRequests,
    -- Device sent duplicate request
    duplicateRequest,
    -- Requested certificate batch not available
    noCertFileAvailable,
    -- RA not able to provide .info file
    noInfoFileAvailable,
    -- RA is not able to provide a current Global Certificate Chain file
    noGlobalCertificateChainFileAvailable, 
    ...
}

-- OBE Triggered Error Codes for Error Logging

ObeError ::= ENUMERATED {
    -- RA-to-EE authentication failed
    authenticationFailed,
    -- EE failed to download 
    globalPolicyFileDownloadFailed,
    -- EE failed to verify the downloaded Global Policy File
    globalPolicyVerificationFailed,
    -- EE failed to parse the Global Policy File
    globalPolicyFileParsingFailed,
    -- EE failed to connect to the RA
    connectionFailed,
    -- EE failed to download the pseudonym certificate batch file
    certFileDownloadFailed,
    -- EE failed to verify the digital signature of an encrypted certificate
    certFileVerificationFailed,
    -- EE failed to decrypt an encrypted certificate
    certFileDecryptionFailed,
    -- EE failed to verify a certificate
    certVerificationFailed,
    -- EE failed to parse certificate or content is incorrect
    certContentFalse,
    -- EE failed to download the *.info file (Misbehaviour Reporting)
    infoFileDownloadFailed,
    -- EE failed to donwload the Global Certificate Chain File
    globalCertifcateChainFileDownloadFailed,
    ...
}

-- RSE Triggered Error Codes

RseError ::= ENUMERATED {
    -- RSE retries within 2 seconds
    retries,
    -- RSE makes more than 10 retries in 60 minutes
    maxRetries,
    -- RSE request is not signed or signature is invalid
    invalidSignature,
    -- RSE has invalid credentials
    invalidCredentials,
    -- RSE makes an unauthorized request / invalid permissions
    invalidRequest,
    -- RSE makes a malformed request
    malformedRequest,
    -- RSE makes a request to an RA that doesn't service it
    raMismatch,
    -- RSE has invalid system time
    invalidTime,
    ...
}


END
