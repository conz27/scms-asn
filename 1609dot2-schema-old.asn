--<OSS.UNBOUNDED SEQUENCE OF>--
--<OSS.UNBOUNDED UTF8String>--
--<OSS.UNBOUNDED IA5String>--
--<OSS.UNBOUNDED OCTET STRING>--
--<OSS.UNBOUNDED BIT STRING>--
--<OSS.LONG>--

IEEE1609dot2 {iso(1) identified-organization(3) ieee(111) 
standards-association-numbered-series-standards(2) wave-stds(1609)  
dot2(2) base (1) schema (1)}
-- 
--********************************************************************** 
-- * IEEE P1609.2 Message Data Types 
-- 
--********************************************************************** 
 DEFINITIONS AUTOMATIC TAGS ::= BEGIN 
 
EXPORTS ALL;

IMPORTS 
  CrlSeries,
  EccNistP256CurvePoint,
  EciesNistP256EncryptedKey,
  GeographicRegion,
  GroupLinkageValue,
  HashAlgorithm,
  HashedId3,
  HashedId8,
  HashedId32,
  Hostname,
  ItsAid,
  ItsAidSsp,
  IValue,
  LinkageValue,
  Opaque,
  PKAlgorithm,
  PublicKey,
  Signature,
  SubjectAssurance,
  SymmetricKey,
  ThreeDLocation,
  Time64,
  Time64WithStandardDeviation,
  Uint3,
  Uint8,
  Uint16, 
  Uint32,
  ValidityPeriod
FROM IEEE1609dot2BaseTypes {iso(1) identified-organization(3) ieee(111) 
    standards-association-numbered-series-standards(2) wave-stds(1609)  
    dot2(2) base(1) base-types(2)}

;

-- 
--********************************************************************** 
-- 
--  Structures for describing secured data
-- 
--**********************************************************************  


  Ieee1609Dot2Data ::= SEQUENCE {
    protocolVersion           Uint8(1),
    messageContent            MessageContent
  }

  MessageContent ::= CHOICE  { 
    unsecuredData     Opaque, 
    signedData        SignedData,
    encryptedData     EncryptedData,
    ...
  }

  SignedData ::= SEQUENCE  { 
    hashId          HashAlgorithm,
    tbsData         ToBeSignedData,
    signer          SignerIdentifier,
    signature       Signature
  }

  SignerIdentifier ::= CHOICE    { 
    digestWithEcdsa256                     HashedId8,
    certificate                            SEQUENCE OF Certificate,
    certificateDigestWithOtherAlgorithm    SEQUENCE  { 
      algorithm   PKAlgorithm,
      digest      HashedId8
    },
    ...
  }

  ToBeSignedData ::= SEQUENCE  { 
    payload         SignedDataPayload,
    headerInfo      HeaderInfo
  }


  HeaderInfo ::= SEQUENCE  { 
      psid                   ItsAid,
      generationTime         Time64WithStandardDeviation OPTIONAL,
      expiryTime             Time64  OPTIONAL,
      generationLocation     ThreeDLocation OPTIONAL,
      missingCertIdentifier  HashedId3 OPTIONAL,
      missingCrlIdentifier   MissingCrlIdentifier OPTIONAL,
      responseEncryptionKey  CHOICE {
          public               PublicKey,
          symmetric            SymmetricKey 
      }                        OPTIONAL,
      ...
  }

  SignedDataPayload ::= SEQUENCE  { 
      data             OCTET STRING OPTIONAL,
      extDataHash      OCTET STRING (SIZE (32)) OPTIONAL,
      ...
  }
      (WITH COMPONENTS {..., data PRESENT} |
       WITH COMPONENTS {..., extDataHash PRESENT})
       -- must include at least one element

  -- NEW, designed to support epidemic distribution in 1609.2 setting.
  MissingCrlIdentifier ::=                  
        SEQUENCE  { caId            HashedId8,
                    crlSeries       Uint32,
                    crlSerial       Uint32,
                    chunkId         Uint16
                  }

  -- New, designed to support aggregated signatures
  Countersignature ::= Ieee1609Dot2Data (WITH COMPONENTS {...,
    messageContent (WITH COMPONENTS {..., 
      signedData  (WITH COMPONENTS {..., 
        tbsData (WITH COMPONENTS {..., 
          payload (WITH COMPONENTS {..., 
            data ABSENT,
            extDataHash PRESENT
          }),
          headerInfo (WITH COMPONENTS {..., 
            psid PRESENT,
            generationTime PRESENT,
            expiryTime ABSENT,
            generationLocation ABSENT,
            missingCertIdentifier ABSENT,
            missingCrlIdentifier ABSENT,
            responseEncryptionKey ABSENT
          })
        })
      })
    })
  })

--********************************************************************** 
-- 
--  Structures for describing encrypted data
-- 
--**********************************************************************  


  EncryptedData ::=
        SEQUENCE  { recipients     SEQUENCE OF RecipientInfo,
                    ciphertext     SymmetricCiphertext
                  }

  -- The three different PKRecipientInfo types are to let the receiver know how
  -- to look up the decryption key:
  -- * certRecipInfo: The data was encrypted using the encryption key in a cert.
  --   This field contains the HashedId8 of the cert.
  -- * signedDataRecipInfo: The data was encrypted using the response encryption
  --   key from a SignedData. This field contains the HashedId8 of the
  --   1609Dot2Data containing the SignedData containing the encryption key.
  -- * rekRecipInfo: The data was encrypted using a response encryption key. The
  --   structure contains the HashedId8 of the response encryption key. This
  --   should only be used if the signedData is not available as it potentially
  --   allows misbinding attacks: it is included in these structures
  --   specifically to enable certificate response encryption from the PCA
  --   to the end-entity device.
  RecipientInfo ::=
        CHOICE    { symmRecipInfo       SymmRecipientInfo,
                    certRecipInfo       PKRecipientInfo, 
                    signedDataRecipInfo PKRecipientInfo, 
                    rekRecipInfo        PKRecipientInfo 
                  }
         
  SymmRecipientInfo ::= OCTET STRING (SIZE(8))

  PKRecipientInfo ::= SEQUENCE  { 
    recipientId        HashedId8, 
      -- recipientId is hash of cert in the case of certRecipInfo, hash of 
      -- signedData that included the response encryption key in the case of 
      -- rekRecipInfo.
    encKey             CHOICE  { 
       eciesNistp256   EciesNistP256EncryptedKey,
       ...
    }
  }

  SymmetricCiphertext ::=
        CHOICE  { aes128ccm           AesCcmCiphertext,
                  ...
                 }

  AesCcmCiphertext ::=
        SEQUENCE  { nonce           OCTET STRING (SIZE (12)),
                    ccmCiphertext   Opaque -- 16 bytes longer than plaintext
                  }


--********************************************************************** 
-- 
--  Certificates and other security management data structures
--  Based more on 103 097 than 1609.2 but with WSA certs and implicit certs
--  supported
-- 
--********************************************************************** 

-- Certificates are implicit (type = implicit, toBeSigned includes 
-- reconstruction value, signature absent) or explicit (type = explicit,
-- toBeSigned includes verification key, signature present).

  Certificate ::= CertificateBase (ImplicitCertificate | ExplicitCertificate)

  CertificateBase ::=
        SEQUENCE  { version                 Uint8(1),
                    type                    CertificateType,
                    issuer                  IssuerIdentifier,
                    toBeSigned              ToBeSignedCertificate,
                    signature               Signature OPTIONAL
                  }
  
  CertificateType  ::= ENUMERATED {
      explicit,
      implicit,
      ...
  }

  ImplicitCertificate ::= CertificateBase (WITH COMPONENTS {...,
      type(implicit),
      toBeSigned(WITH COMPONENTS {..., 
          verificationKey ABSENT, 
          reconstructionValue PRESENT
      }), 
      signature ABSENT
  })

  ExplicitCertificate ::= CertificateBase (WITH COMPONENTS {...,
      type(explicit),
      toBeSigned(WITH COMPONENTS {..., 
          verificationKey PRESENT, 
          reconstructionValue ABSENT
      }), 
      signature PRESENT
  })

  IssuerIdentifier ::= CHOICE  { 
    ecdsaNistP256AndDigest  HashedId8,
    algorithmAndDigest      SEQUENCE  { 
        algorithm           PKAlgorithm,
        digest              HashedId8
    }
  }

  ToBeSignedCertificate ::= SEQUENCE  { 
    validityPeriod          ValidityPeriod,
    region                  GeographicRegion OPTIONAL,
    crlSeries               CrlSeries,
    scope                   CHOICE { 
      pseudonym             PseudonymScope, 
      authorization         AuthScope, 
      enrollment            EnrollmentScope,
      ca                    CaScope,
      ...
    },
    encryptionKey           PublicKey OPTIONAL,
    verificationKey         PublicKey OPTIONAL,
    reconstructionValue     EccNistP256CurvePoint OPTIONAL,
    ...
  }
  (WITH COMPONENTS { ..., verificationKey PRESENT} |
   WITH COMPONENTS { ..., reconstructionValue PRESENT})



  PseudonymScope ::= 
        SEQUENCE  { linkageData           LinkageData,
                    psidSsp               SEQUENCE OF ItsAidSsp,
                    assuranceLevel        SubjectAssurance OPTIONAL
                  }

  LinkageData ::= 
        SEQUENCE  { iValue                IValue,
                    linkage-value         LinkageValue, 
                    group-linkage-value   GroupLinkageValue OPTIONAL
                  }
         

  AuthScope ::= 
        SEQUENCE  { name                  Hostname,
                    psidSsp               SEQUENCE OF ItsAidSsp,
                    assuranceLevel        SubjectAssurance OPTIONAL
                  }

-- Certs with an EnrollmentScope are implicitly allowed to sign messages with 
-- PSID = 0x23 and and NOT allowed to sign messages with other PSIDs.
  EnrollmentScope ::= SEQUENCE  { 
      name                Hostname,
      auths               CHOICE {
          pseudonym-auths     SEQUENCE OF ItsAidSsp,
          authorization-auths SEQUENCE OF ItsAidSsp,
      ...
      }
  }


  CaScope ::= SEQUENCE  { 
      name                Hostname,
      auths               CHOICE {
          end-entity-auths  SEQUENCE {
              pseudonym-auths     CaAuths OPTIONAL,
              authorization-auths CaAuths OPTIONAL,
              enrollment-auths    CHOICE {
                  pseud               CaAuths,
                  auth                CaAuths
              } OPTIONAL
          },
          ca-auths            InnerCaScope,
          ...
      }
  }

  InnerCaScope ::= CHOICE {
      end-entity-auths    SEQUENCE  { 
          pseudonym-auths     SEQUENCE OF ItsAid OPTIONAL,
          authorization-auths SEQUENCE OF ItsAid OPTIONAL,
          enrollment-auths    SEQUENCE OF ItsAid OPTIONAL
      }
      ca-auths            SEQUENCE OF ItsAid,
      ...
  }

  CaAuths ::= SEQUENCE {
      psid-all-ssps           SEQUENCE OF ItsAid OPTIONAL,
      psid-restricted-ssps    SEQUENCE OF ItsAidSsp OPTIONAL,
      ... -- could in future support regex matching
  }




-- Certs with a CaScope are implicitly allowed to sign messages with 
-- PSID = 0x23.

    
 



  
--********************************************************************** 
-- Data Types required for internal processing of transmitted and received
-- data but which are not needed for transmitted messages.
--
--********************************************************************** 

  PublicKeyReconstructionHashInput ::= -- Note, reverse order from 1609.2
        SEQUENCE  { subjectCertificate      Certificate,
                    issuerHash              HashedId32
                  }


END
