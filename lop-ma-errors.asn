Ieee1609Dot2LopMaError
{iso(1) identified-organization(3) ieee(111) 
standards-association-numbered-series-standards(2) wave-stds(1609)  
dot2(2) scms(2) errors(2) lop-ma (12)}

DEFINITIONS AUTOMATIC TAGS ::= BEGIN

EXPORTS ALL;

LopMaError ::= ENUMERATED {
  start(1), --not used yet
  ...
}



END
