Ieee1609Dot2ScmsDownloadAuthentication
{iso(1) identified-organization(3) ieee(111) 
standards-association-numbered-series-standards(2) wave-stds(1609)  
dot2(2) scms(2) interfaces(1) download-authentication (138)}

DEFINITIONS AUTOMATIC TAGS ::= BEGIN

EXPORTS ALL;

IMPORTS 
  Time32
  FROM IEEE1609dot2BaseTypes {iso(1) identified-organization(3) ieee(111) 
    standards-association-numbered-series-standards(2) wave-stds(1609) dot2(2)
    base(1) base-types(2)}

  SecurityMgmtPsid
  FROM Ieee1609dot2ScmsBaseTypes {iso(1) identified-organization(3) ieee(111)
	standards-association-numbered-series-standards(2) wave-stds(1609)  dot2(2)
	scms (2) interfaces(1) base-types (2)}

  ScmsPDU,
  SecuredScmsPDU
  FROM
    IEEE1609dot2ScmsProtocol {iso(1) identified-organization(3) ieee(111) 
standards-association-numbered-series-standards(2) wave-stds(1609)  
dot2(2) scms(2) interfaces(1) protocol(1)}
    
;

AuthenticatedDownloadRequest ::= SEQUENCE {
    timestamp      Time32,
    filename       UTF8String (SIZE(0..255)),
    ...
} 


ScopedAuthenticatedDownloadRequest ::= 
  ScmsPDU  (WITH COMPONENTS {...,
    content (WITH COMPONENTS {
      ee-ra (WITH COMPONENTS {
        authenticatedDownloadRequest
      })
    })
  })

SignedAuthenticatedDownloadRequest ::= SecuredScmsPDU (WITH COMPONENTS {...,
  content (WITH COMPONENTS {..., 
    signedData  (WITH COMPONENTS {..., 
      tbsData (WITH COMPONENTS {..., 
        payload (WITH COMPONENTS {..., 
          data (WITH COMPONENTS {...,
             content (WITH COMPONENTS {
                unsecuredData (CONTAINING ScopedAuthenticatedDownloadRequest)
            })
          })
        }),
        headerInfo (WITH COMPONENTS {..., 
          psid (SecurityMgmtPsid),
          generationTime ABSENT,
          expiryTime ABSENT,
          generationLocation ABSENT,
          p2pcdLearningRequest ABSENT,
          missingCrlIdentifier ABSENT,
          encryptionKey ABSENT
        })
      })
    })
  })
})


END
