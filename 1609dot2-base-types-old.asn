--<OSS.UNBOUNDED SEQUENCE OF>--
--<OSS.UNBOUNDED UTF8String>--
--<OSS.UNBOUNDED IA5String>--
--<OSS.UNBOUNDED OCTET STRING>--
--<OSS.UNBOUNDED BIT STRING>--
--<OSS.LONG>--

IEEE1609dot2BaseTypes {iso(1) identified-organization(3) ieee(111) 
standards-association-numbered-series-standards(2) wave-stds(1609)  
dot2(2) base(1) base-types(2)}

-- 
--********************************************************************** 
-- * IEEE P1609.2 Message Data Types 
-- 
--********************************************************************** 
 DEFINITIONS AUTOMATIC TAGS ::= BEGIN 
 
EXPORTS ALL;


  -- ------------------------------------------------------------------
  -- 
  -- Integers
  --
  -- ------------------------------------------------------------------


  Uint3  ::= INTEGER (0..7)                    -- (hex)                      07
  Uint8  ::= INTEGER (0..255)                  -- (hex)                      ff
  Uint16 ::= INTEGER (0..65535)                -- (hex)                   ff ff
  Uint32 ::= INTEGER (0..4294967295)--<LONGLONG>-- -- (hex)             ff ff ff ff
  Uint64 ::= INTEGER (0..18446744073709551615) -- (hex) ff ff ff ff ff ff ff ff

  -- ------------------------------------------------------------------
  -- 
  -- OCTET STRING types
  --
  -- ------------------------------------------------------------------


  Opaque ::= OCTET STRING

  
  HashedId32 ::= OCTET STRING (SIZE(32))
  HashedId10 ::= OCTET STRING (SIZE(10))
  HashedId8  ::= OCTET STRING (SIZE(8))
  HashedId4  ::= OCTET STRING (SIZE(4))
  HashedId3  ::= OCTET STRING (SIZE(3))

  -- ------------------------------------------------------------------
  -- 
  -- Time
  --
  -- ------------------------------------------------------------------

  Time32 ::= Uint32
  Time64 ::= Uint64
  Time64WithStandardDeviation ::=
        SEQUENCE  { time        Time64,
                    logStdDev   Uint8
                  }

  ValidityPeriod ::=
        CHOICE  { expiryOnly          Time32,
                  startAndExpiry      SEQUENCE  { expiry         Time32,
                                                  startValidity  Time32
                                                },
                  durationAndExpiry   SEQUENCE  { expiry         Time32,
                                                  duration       Duration
                                                }
                  -- should be expiryAndDuration obviously
                }

  Duration ::=
        SEQUENCE  { timeUnit            TimeUnit,       
                    timeValue           INTEGER(0..8191)
                  } 

  TimeUnit ::=  ENUMERATED {
    seconds,
    minutes,
    hours,
    sixtyHours,
    years 
  }

  -- ------------------------------------------------------------------
  -- 
  -- Location
  --
  -- ------------------------------------------------------------------


  GeographicRegion ::=
        CHOICE  { circularRegion      CircularRegion,
                  rectangularRegion   SEQUENCE OF RectangularRegion,
                  polygonalRegion     PolygonalRegion,
                  identifiedRegion    IdentifiedRegion,
                  ...
                }

  CircularRegion ::=
        SEQUENCE  { center          TwoDLocation,
                    radius          Uint16
                  }

  RectangularRegion ::=
        SEQUENCE  { northWest       TwoDLocation,
                    southEast       TwoDLocation
                  }

  PolygonalRegion ::= SEQUENCE SIZE(3..12) OF TwoDLocation

  TwoDLocation ::=
        SEQUENCE  { latitude      Latitude,
                    longitude     Longitude
                  }

  IdentifiedRegion ::= 
        CHOICE    { iso3166       ISO31661Region,
                    un-stats      UNStatsRegion,
                    ...
                  }

  ISO31661Region ::= 
        SEQUENCE  { iso31661CountryCode  INTEGER (0..999),
                    local                Uint32
                  }
  UNStatsRegion ::=
        SEQUENCE  { unStatsCountryCode   Uint16,
                    local                Uint32
                  }
  ThreeDLocation ::=
        SEQUENCE  { latitude        Latitude,
                    longitude       Longitude,
                    elevation       Elevation
                  }

  Latitude ::= NinetyDegreeInt
  Longitude ::= OneEightyDegreeInt
  Elevation ::= ElevInt

  NinetyDegreeInt ::= INTEGER {
		min 		(-900000000),
		max 		(900000000),
		unknown 	(900000001)
  } (-900000000..900000001)

  KnownLatitude ::= NinetyDegreeInt (min..max) -- Minus 90deg to +90deg in microdegree intervals
  UnknownLatitude ::= NinetyDegreeInt (unknown)
  
  OneEightyDegreeInt ::= INTEGER {
		min      	(-1800000000),
		max      	(1800000000),
		unknown  	(1800000001)
  } (-1800000000..1800000001)

  KnownLongitude ::= OneEightyDegreeInt (min..max) -- Minus 180deg to +180deg in microdegree intervals
  UnknownLongitude ::= OneEightyDegreeInt (unknown)
  
  ElevInt ::= INTEGER  {
		max  		(61439),
		min  		(-4095),
		unknown		(-4096)
  } (-4096..61439)

  MaxElev ::= ElevInt (max)
  MinElev ::= ElevInt (min)
  KnownElev ::= ElevInt (min..max)  -- Minus 409.5m to 6143.9m in 0.1m intervals
  UnknownElev ::= ElevInt (unknown)

  -- ------------------------------------------------------------------
  -- 
  -- Crypto
  --
  -- ------------------------------------------------------------------

  Signature ::=
        CHOICE  { ecdsa256Signature EcdsaNistP256Signature,
                  ...
                }
  EcdsaNistP256Signature ::= -- note: alternative is to import from X9.62 / SEC 1
        SEQUENCE {  r     EccNistP256CurvePoint,
                    s     OCTET STRING (SIZE (32))
                 }

  EccCurvePoint ::=
        CHOICE   {  ecc256           EccNistP256CurvePoint,
                    ...
                 }
  EccNistP256CurvePoint ::= -- note: alternative is to import from X9.62 / SEC 1
        CHOICE    { x-only           OCTET STRING (SIZE (32)),
                    fill             NULL,  -- consistency with 1363 / X9.62
                    compressed-y-0   OCTET STRING (SIZE (32)),
                    compressed-y-1   OCTET STRING (SIZE (32)),
                    uncompressed     SEQUENCE {
                                       x OCTET STRING (SIZE (32)),
                                       y OCTET STRING (SIZE (32))
                                     }
                  }

  EccNistP256CurvePrivateKeyReconstruction ::=  OCTET STRING (SIZE (32))

  PKAlgorithm ::= ENUMERATED  { 
      ecdsaNistp256WithSha256,
      eciesNistp256,
      ...
  } 

  SymmAlgorithm ::= ENUMERATED  { 
      aes128Ccm,
      ...
  }

  HashAlgorithm ::= ENUMERATED  { 
      sha256,
      ...
  }

  EciesNistP256EncryptedKey ::=
        SEQUENCE  { v               EccNistP256CurvePoint,
                    c               OCTET STRING (SIZE (16)),
                    t               OCTET STRING (SIZE (16)) -- inconsistent with .2 but fixes long-standing annoyance
                  }

  
  PublicKey ::=
        CHOICE  { ecdsaVerificationKey      EccCurvePoint,
                  eciesEncryptionKey        SEQUENCE  { supportedSymmAlg  SymmAlgorithm,
                                                        publicKey         EccCurvePoint
                                                      },
                  ...
                }

  SymmetricKey ::= CHOICE {
      aes128Ccm     OCTET STRING(SIZE(16)),
      ...
  }

  -- ------------------------------------------------------------------
  -- 
  -- PSID / ITS-AID
  --
  -- ------------------------------------------------------------------


   ItsAidSsp ::= 
        SEQUENCE  { psid       ItsAid,
                    ssp        OCTET STRING (SIZE(0..MAX))
                  }
                  

  ItsAid ::= Uint32 -- should at least be unsigned

  -- ------------------------------------------------------------------
  -- 
  -- Goes in certs
  --
  -- ------------------------------------------------------------------

  SubjectAssurance ::= OCTET STRING (SIZE(1))

  CrlSeries ::= Uint32

  

  -- ------------------------------------------------------------------
  -- 
  -- Pseudonym Linkage
  --
  -- ------------------------------------------------------------------

  IValue ::= Uint16
  Hostname ::= UTF8String (SIZE(0..256))
  LinkageValue ::= OCTET STRING (SIZE(9))
  GroupLinkageValue ::= SEQUENCE {
    jValue  OCTET STRING (SIZE(3)),
    value   OCTET STRING (SIZE(10))
  }
  
END
