--
--  Copyright 2017, 2018 Crash Avoidance Metrics Partner, VSC5 Consortium
--
--  Licensed under the Apache License, Version 2.0 (the "License");
--  you may not use this file except in compliance with the License.
--  You may obtain a copy of the License at
--
--     http://www.apache.org/licenses/LICENSE-2.0
--
--  Unless required by applicable law or agreed to in writing, software
--  distributed under the License is distributed on an "AS IS" BASIS,
--  WITHOUT WARRANTIES OR CONDITIONS OF ANY KIND, either express or implied.
--  See the License for the specific language governing permissions and
--  limitations under the License.
--

-------------------------------------------------------------------------------
-- ECA-EE 
--
-- The structures in this file define the protocol for messages between the
-- ECA and any EE (OBE or RSE) for the purpose of requesting and receiving
-- a new enrollment certificate.
--
-- The enrollment process is always initiated by the EE, typically with the aid
-- of a DCM which provides a trusted connection between the new EE and the
-- ECA.  The enrollment protocol assumes that the DCM does not take an active
-- roll in the enrollment certificate request/response, it is just a trusted
-- network connection point for the EE.  
--
-- This file is part of the SCMS protocol developed by CAMP VSC5
-- It depends on the IEEE 1609.2 protocol specification
-------------------------------------------------------------------------------

-- @namespace Ieee1609Dot2EcaEndEntityInterface
Ieee1609Dot2EcaEndEntityInterface
{iso(1) identified-organization(3) ieee(111)
standards-association-numbered-series-standards(2) wave-stds(1609)
dot2(2) scms(4) interfaces(1) eca-ee (5) major-version-2(2)}

DEFINITIONS AUTOMATIC TAGS ::= BEGIN

EXPORTS ALL;

IMPORTS

  HashedId8,
  Time32,
  Uint8
FROM IEEE1609dot2BaseTypes {iso(1) identified-organization(3) ieee(111)
	 standards-association-numbered-series-standards(2) wave-stds(1609)
	 dot2(2) base(1) base-types(2) major-version-2(2)}

  Certificate,
  ImplicitCertificate,
  ToBeSignedCertificate
FROM IEEE1609dot2 {iso(1) identified-organization(3) ieee(111)
	 standards-association-numbered-series-standards(2) wave-stds(1609)
	 dot2(2) base (1) schema (1) major-version-2(2)}

  EccP256PrivateKeyReconstruction
FROM Ieee1609dot2ScmsBaseTypes {iso(1) identified-organization(3) ieee(111)
     standards-association-numbered-series-standards(2) wave-stds(1609)  dot2(2)
     scms(4) interfaces(1) base-types (2) major-version-2(2)}

;

---
-- @brief The EcaEndEntityInterfacePDU is the parent message type for messages 
--        sent between Enrollment Certificate Authority (ECA) and End Entities
--        (EE).
-- @class EcaEndEntityInterfacePDU
-- @param eeEcaCertRequest  contains the enrollment certificate request sent
--                          by the EE to the ECA.
-- @param ecaEeCertResponse contains the enrollment certificate response sent
--                          by the ECA to an EE.
EcaEndEntityInterfacePDU::= CHOICE {
    eeEcaCertRequest 	EeEcaCertRequest,
    ecaEeCertResponse 	EcaEeCertResponse,
    ...
}

---
-- @brief This data type is used by the EE to request an enrollment 
--        certificate from the ECA. It is signed using the private key 
--        generated by the EE and the corresponding public key is placed in 
--        verificationKey for use by the ECA to generate the enrollment
--        certificate. All the fields of ToBeSignedCertificate are filled by
--        the EE/DCM, but the ECA may override them.
-- @class EeEcaCertRequest
-- @param version     contains the current version of the data type. The 
--                    version specified in this document is version 1,
--                    represented by the integer 1.
-- @param currentTime contains the time of creation of EeEcaCertRequest.
-- @param tbsData     contains the ToBeSignedCertificate data used by the ECA 
--                    to generate the EE's enrollment certificate. The 
--                    ToBeSignedCertificate is specified in Section 6.4.8 of
--                    IEEE 1609.2-2016.
-- @see Uint8, Time32, ToBeSignedCertificate
EeEcaCertRequest ::= SEQUENCE {
    version             Uint8(1),
    currentTime         Time32,
    tbsData             ToBeSignedCertificate (WITH COMPONENTS { ...,
      id(WITH COMPONENTS { ...,
        linkageData ABSENT }),
      region PRESENT,
      appPermissions ABSENT,
      certIssuePermissions ABSENT,
      certRequestPermissions PRESENT,
      encryptionKey ABSENT,
      verifyKeyIndicator (WITH COMPONENTS {
        verificationKey }) }),
    ...
}

---
-- @brief This data type is used by the ECA to respond to an EE's enrollment 
--        certificate request. Additional bootstrapping information including 
--        the RA's certificate are provided by the DCM in a zipped file.
-- @class EcaEeCertResponse
-- @param version               contains the current version of the data type. 
--                              The version specified in this document is 
--                              version 1, represented by the integer 1.
-- @param requestHash           contains the hash of the original
--                              EeEcaCertRequest message.
-- @param ecaCert               contains the Enrollment Certificate Authority
--                              certificate.
-- @param enrollmentCert        contains the Implicit Certificate structure of 
--                              the enrollment certificate, as specified in
--                              Section 6.4.5 of IEEE 1609.2-2016.
-- @param privKeyReconstruction contains the private key reconstruction value 
--                              required by the EE to transform its private
--                              key into an operational private key.
-- @see Uint8, HashedId8, Certificate, ImplicitCertificate,
--      EccP256PrivateKeyReconstruction
EcaEeCertResponse ::= SEQUENCE {
	version         Uint8(1),
    requestHash     			HashedId8,
    ecaCert         Certificate,
    enrollmentCert  			ImplicitCertificate,
    privKeyReconstruction 		EccP256PrivateKeyReconstruction,
    ...
}

END
