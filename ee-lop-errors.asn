Ieee1609Dot2EndEntityLopError
{iso(1) identified-organization(3) ieee(111) 
standards-association-numbered-series-standards(2) wave-stds(1609)  
dot2(2) scms(2) errors(2) ee-lop (6)}

DEFINITIONS AUTOMATIC TAGS ::= BEGIN

EXPORTS ALL;

EndEntityLopError ::= ENUMERATED {
  start(1), -- not used yet
  ...
}



END
