Ieee1609Dot2EndEntityLopInterface
{iso(1) identified-organization(3) ieee(111) 
standards-association-numbered-series-standards(2) wave-stds(1609)  
dot2(2) scms(2) interfaces(1) ee-lop (6)}

DEFINITIONS AUTOMATIC TAGS ::= BEGIN

EXPORTS ALL;

IMPORTS 
  Uint8
FROM IEEE1609dot2BaseTypes {iso(1) identified-organization(3) ieee(111) 
		standards-association-numbered-series-standards(2) wave-stds(1609)  
		dot2(2) base(1) base-types(2)}

  ScopedEndEntityLopError

FROM Ieee1609dot2ScmsError {iso(1) identified-organization(3) ieee(111) 
		standards-association-numbered-series-standards(2) wave-stds(1609)  
		dot2(2) scms(2) errors(2) complete (1)}

;


EndEntityLopInterfacePDU::= CHOICE {
    placeholder Uint8(1),
    ...
}


END
