Ieee1609Dot2DcmEndEntityError
{iso(1) identified-organization(3) ieee(111) 
standards-association-numbered-series-standards(2) wave-stds(1609)  
dot2(2) scms(2) errors(2) dcm-ee (127)}

DEFINITIONS AUTOMATIC TAGS ::= BEGIN

EXPORTS ALL;

DcmEndEntityError ::= ENUMERATED {
  start(1), -- not used yet
  ...
}



END
