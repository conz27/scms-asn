IEEE1609dot2BaseTypes {iso(1) identified-organization(3) ieee(111) 
standards-association-numbered-series-standards(2) wave-stds(1609)  
dot2(2) base(1) base-types(2)}

-- 
--********************************************************************
-- * IEEE P1609.2 Base Data Types 
-- 
--******************************************************************** 
 DEFINITIONS AUTOMATIC TAGS ::= BEGIN 
 
EXPORTS ALL;


  -- ------------------------------------------------------------------
  -- 
  -- Integers
  --
  -- ------------------------------------------------------------------


  Uint3  ::= INTEGER (0..7)                    -- (hex)                      07
  Uint8  ::= INTEGER (0..255)                  -- (hex)                      ff
  Uint16 ::= INTEGER (0..65535)                -- (hex)                   ff ff
  Uint32 ::= INTEGER (0..4294967295)--<LONGLONG>-- -- (hex)             ff ff ff ff
  Uint64 ::= INTEGER (0..18446744073709551615) -- (hex) ff ff ff ff ff ff ff ff

  -- ------------------------------------------------------------------
  -- 
  -- OCTET STRING types
  --
  -- ------------------------------------------------------------------


  Opaque ::= OCTET STRING

  
  HashedId32 ::= OCTET STRING (SIZE(32))
  HashedId10 ::= OCTET STRING (SIZE(10))
  HashedId8  ::= OCTET STRING (SIZE(8))
  HashedId4  ::= OCTET STRING (SIZE(4))
  HashedId3  ::= OCTET STRING (SIZE(3))

  -- ------------------------------------------------------------------
  -- 
  -- Time
  --
  -- ------------------------------------------------------------------

  Time32 ::= Uint32
  Time64 ::= Uint64
  Time64WithStandardDeviation ::=
        SEQUENCE  { time        Time64,
                    logStdDev   Uint8
                  }

  ValidityPeriod ::= SEQUENCE {
      start          Time32,
      duration       Duration
  }

  Duration ::= CHOICE {
      microseconds     Uint16,
      milliseconds     Uint16,
      seconds          Uint16,
      minutes          Uint16,
      hours            Uint16,
      sixtyHours       Uint16,
      years            Uint16
  } 

  -- ------------------------------------------------------------------
  -- 
  -- Location
  --
  -- ------------------------------------------------------------------


GeographicRegion ::=
        CHOICE  { circularRegion      CircularRegion,
                  rectangularRegion   SequenceOfRectangularRegion,
                  polygonalRegion     PolygonalRegion,
                  identifiedRegion    SequenceOfIdentifiedRegion,
                  ...
                }

  CircularRegion ::=
        SEQUENCE  { center          TwoDLocation,
                    radius          Uint16
                  }

  RectangularRegion ::=
        SEQUENCE  { northWest       TwoDLocation,
                    southEast       TwoDLocation
                  }

  SequenceOfRectangularRegion ::= SEQUENCE OF RectangularRegion

  PolygonalRegion ::= SEQUENCE SIZE(3..12) OF TwoDLocation

  TwoDLocation ::=
        SEQUENCE  { latitude      Latitude,
                    longitude     Longitude
                  }

  IdentifiedRegion ::= 
        SEQUENCE  { unStatsCountryCode   Uint16,
                    local                Uint32 DEFAULT 0
                  }

  SequenceOfIdentifiedRegion ::= SEQUENCE OF IdentifiedRegion


  ThreeDLocation ::=
        SEQUENCE  { latitude        Latitude,
                    longitude       Longitude,
                    elevation       Elevation
                  }

  Latitude ::= NinetyDegreeInt
  Longitude ::= OneEightyDegreeInt
  Elevation ::= ElevInt

  NinetyDegreeInt ::= INTEGER {
		min 		(-900000000),
		max 		(900000000),
		unknown 	(900000001)
  } (-900000000..900000001)

  KnownLatitude ::= NinetyDegreeInt (min..max) -- Minus 90deg to +90deg in microdegree intervals
  UnknownLatitude ::= NinetyDegreeInt (unknown)
  
  OneEightyDegreeInt ::= INTEGER {
		min      	(-1800000000),
		max      	(1800000000),
		unknown  	(1800000001)
  } (-1800000000..1800000001)

  KnownLongitude ::= OneEightyDegreeInt (min..max) -- Minus 180deg to +180deg in microdegree intervals
  UnknownLongitude ::= OneEightyDegreeInt (unknown)
  
  ElevInt ::= INTEGER  {
		max  		(61439),
		min  		(-4095),
		unknown		(-4096)
  } (-4096..61439)

  MaxElev ::= ElevInt (max)
  MinElev ::= ElevInt (min)
  KnownElev ::= ElevInt (min..max)  -- Minus 409.5m to 6143.9m in 0.1m intervals
  UnknownElev ::= ElevInt (unknown)

  -- ------------------------------------------------------------------
  -- 
  -- Crypto
  --
  -- ------------------------------------------------------------------

  Signature ::=
        CHOICE  { ecdsa256Signature EcdsaNistP256Signature,
                  ...
                }
  EcdsaNistP256Signature ::= -- note: alternative is to import from X9.62 / SEC 1
        SEQUENCE {  r     EccNistP256CurvePoint,
                    s     OCTET STRING (SIZE (32))
                 }

  EccCurvePoint ::=
        CHOICE   {  ecc256           EccNistP256CurvePoint,
                    ...
                 }
  EccNistP256CurvePoint ::= -- note: alternative is to import from X9.62 / SEC 1
        CHOICE    { x-only           OCTET STRING (SIZE (32)),
                    fill             NULL,  -- consistency with 1363 / X9.62
                    compressed-y-0   OCTET STRING (SIZE (32)),
                    compressed-y-1   OCTET STRING (SIZE (32)),
                    uncompressed     SEQUENCE {
                                       x OCTET STRING (SIZE (32)),
                                       y OCTET STRING (SIZE (32))
                                     }
                  }

  EccNistP256CurvePrivateKeyReconstruction ::=  OCTET STRING (SIZE (32))

  PKAlgorithm ::= ENUMERATED  { 
      ecdsaNistp256WithSha256,
      eciesNistp256,
      ...
  } 

  SymmAlgorithm ::= ENUMERATED  { 
      aes128Ccm,
      ...
  }

  HashAlgorithm ::= ENUMERATED  { 
      sha256,
      ...
  }

  EciesNistP256EncryptedKey ::=
        SEQUENCE  { v               EccNistP256CurvePoint,
                    c               OCTET STRING (SIZE (16)),
                    t               OCTET STRING (SIZE (16))
                  }

  EncryptionKey ::= CHOICE {
          public               PublicEncryptionKey,
          symmetric            SymmetricEncryptionKey 
  }

  PublicEncryptionKey ::= SEQUENCE  { 
          supportedSymmAlg      SymmAlgorithm,
          publicKey             BasePublicEncryptionKey
      }

  BasePublicEncryptionKey ::= CHOICE { 
          eciesNistP256      EccNistP256CurvePoint,
          ...
      }

  PublicVerificationKey ::= CHOICE  { 
      ecdsaNistP256             EccNistP256CurvePoint,
      ...
  }

  SymmetricEncryptionKey ::= CHOICE {
      aes128Ccm     OCTET STRING(SIZE(16)),
      ...
  }

  -- ------------------------------------------------------------------
  -- 
  -- PSID / ITS-AID
  --
  -- ------------------------------------------------------------------


  Psid ::= INTEGER (0..MAX)

  PsidSsp ::= SEQUENCE {
      psid                  Psid,
      ssp                   Ssp OPTIONAL
  }

  Ssp ::= CHOICE {
      opaque              OCTET STRING (SIZE(0..MAX)),
      ... -- will define Structured SSP here
  }

  PsidSspRange ::= SEQUENCE {
      psid                Psid,
      sspRange            SspRange OPTIONAL
  }

  SspRange ::= CHOICE {
      opaque              SequenceOfOctetString,
      all                 NULL,
      ... -- will define Structured SSP Range here
  }
    

  SequenceOfPsid ::= SEQUENCE OF Psid
  SequenceOfPsidSsp::= SEQUENCE OF PsidSsp
  SequenceOfPsidSspRange ::= SEQUENCE OF PsidSspRange
  SequenceOfOctetString ::= SEQUENCE OF OCTET STRING


  -- ------------------------------------------------------------------
  -- 
  -- Goes in certs
  --
  -- ------------------------------------------------------------------

  SubjectAssurance ::= OCTET STRING (SIZE(1))

  CrlSeries ::= Uint16
  

  -- ------------------------------------------------------------------
  -- 
  -- Pseudonym Linkage
  --
  -- ------------------------------------------------------------------

  IValue ::= Uint16
  Hostname ::= UTF8String (SIZE(0..256))
  LinkageValue ::= OCTET STRING (SIZE(9))
  GroupLinkageValue ::= SEQUENCE {
    jValue  OCTET STRING (SIZE(3)),
    value   OCTET STRING (SIZE(10))
  }
  LinkageSeed ::= OCTET STRING (SIZE(16))
  LaId ::= OCTET STRING (SIZE(2)) 

END
